FME workspace Laboratoire2.fmw

Parameters:
- DestDataset_MBTILES =
- DestDataset_POSTGIS =
- DestDataset_POSTGIS_7 =
- DestDataset_POSTGIS_8 =
- DestDataset_POSTGIS_9 =
- DestDataset_POSTGIS_RASTER =
- DestDataset_POSTGIS_RASTER_4 =
- DestDataset_POSTGIS_RASTER_5 =
- SourceDataset_GEOTIFF =
- SourceDataset_GEOTIFF_3 =
- SourceDataset_PNGRASTER =

Readers:
- PNGRASTER_1: PNGRASTER from $(SourceDataset_PNGRASTER)
- GEOTIFF_1: GEOTIFF from $(SourceDataset_GEOTIFF)
- GEOTIFF_2: GEOTIFF from $(SourceDataset_GEOTIFF_3) in EPSG:32188

Writers:
- POSTGIS_RASTER_1: POSTGIS_RASTER to $(DestDataset_POSTGIS_RASTER)
- POSTGIS_1: POSTGIS to $(DestDataset_POSTGIS)
- POSTGIS_2: POSTGIS to $(DestDataset_POSTGIS_9)
- POSTGIS_3: POSTGIS to $(DestDataset_POSTGIS_7)
- POSTGIS_4: POSTGIS to $(DestDataset_POSTGIS_8)
- MBTILES_1: MBTILES to $(DestDataset_MBTILES)
- POSTGIS_RASTER_2: POSTGIS_RASTER to $(DestDataset_POSTGIS_RASTER_5)
- POSTGIS_RASTER_3: POSTGIS_RASTER to $(DestDataset_POSTGIS_RASTER_4)

GEOTIFF (reader GEOTIFF_2)
    -> Reprojector_2
Note: 32188 vers 3857
Reprojector_2
    DEST = EPSG:3857
    INTERPOLATION_TYPE_NAME = Nearest Neighbor
    RASTER_CELL_SIZE = Preserve Cells
    RASTER_TOLERANCE = 0.0
    SOURCE = EPSG:32188
    REPROJECTED -> ContourGenerator [POINTS/LINES]
    REPROJECTED -> RasterInterpretationCoercer
    REPROJECTED -> RasterCellValueRounder_2
    REPROJECTED -> RasterHillshader
GEOTIFF (reader GEOTIFF_1)
    -> Reprojector
    -> RasterPropertyExtractor_2
PNGRASTER (reader PNGRASTER_1)
    -> RasterPropertyExtractor
    -> Reprojector_3
Logger
    LOG_FEATURE = LOG_ONLY
    MAXCOORDS = 20
    MAXFEATS = 20
    MESSAGE = Feature is:
    SEVERITY = INFO
Logger_2
    LOG_FEATURE = LOG_ONLY
    MAXCOORDS = 20
    MAXFEATS = 20
    MESSAGE = Feature is:
    SEVERITY = INFO

Bookmark: MNS - Ville Marie 1m VERS Vecteurs
Note: Génère les contours depuis le raster
ContourGenerator
    CONTOUR_DIMENSION = 3
    CONTOUR_INTERVAL = 10
    ELEV_ATTR = _elevation
    IGNORE_INPUT_ON_INTERVAL = Perturb Input Points On Contour Interval
    TOLERANCE = 0
    CONTOURS -> Generalizer
Note: Simplifie par 10 le nbre de vertex
Generalizer
    ALG_TEXT = Douglas (Generalize)
    PRESERVE = No
    PRESERVE_PATHS = No
    TOLERANCE = 10
    -> AreaBuilder
    <REJECTED> -> Generalizer__Rejected_
Note: Ligne to polygones
AreaBuilder
    ALLOW_CYCLES = No
    CHECK_CURVE_DIRECTION = No
    CONNECT_Z_MODE = First Wins
    CONSIDER_NODE_ELEVATION = no
    DEAGGREGATE_INPUT = Deaggregate
    DONUT_CREATION = YES
    DROP_HOLES = No
    LINES_AS_SEGMENTS = No
    POLY_ACCUM_ATTRS_NAME = Use Attributes From One Feature
    SNAPTYPE_PARAM = None
    AREA -> mns_contour_polygones (writer POSTGIS_4)
    <REJECTED> -> AreaBuilder__Rejected_
mns_contour_polygones (writer POSTGIS_4)
    attributes: _elevation float8
AreaBuilder__Rejected_: Logger
    LOG_FEATURE = LOG_ONLY
    MAXCOORDS = 20
    MAXFEATS = 20
    MESSAGE = Feature is:
    SEVERITY = INFO
Generalizer__Rejected_: Logger
    LOG_FEATURE = LOG_ONLY
    MAXCOORDS = 20
    MAXFEATS = 20
    MESSAGE = Feature is:
    SEVERITY = INFO

Bookmark: MNS - Ville Marie 1m VERS Tuiles
Note: De 1 bande à 3 bandes (RGB)
RasterInterpretationCoercer
    COLOR_TO_COLOR = Scale by data type
    FLOAT_TO_INTEGER = Round
    INTERPRETATION = RGBA32
    NUMERIC_TO_COLOR = Scale by data values
    RGB_TO_RGBA = Create opaque alpha band
    -> mns_to_mbtiles (writer MBTILES_1)
    <REJECTED> -> Logger_6
Note: Génère un fichier de tuiles mbtiles spécialiement pour les applications web mapbox gl
mns_to_mbtiles (writer MBTILES_1)
Logger_6
    LOG_FEATURE = LOG_ONLY
    MAXCOORDS = 20
    MAXFEATS = 20
    MESSAGE = Feature is:
    SEVERITY = INFO
Note: Simplifie le Z
RasterCellValueRounder_2
    PLACES = 0
    ROUND_TYPE = nearest
    -> RasterTiler
    -> WebMapTiler
    <REJECTED> -> Logger_4
Note: Divise le raster en 10x10 tuiles plus petites
RasterTiler
    FORCE_EQUAL_SIZED_TILES = No
    NUM_HORIZONTAL_TILES = 10
    NUM_HORIZONTAL_TILES_ATTRIBUTE = _num_tile_columns
    NUM_VERTICAL_TILES = 10
    NUM_VERTICAL_TILES_ATTRIBUTE = _num_tile_rows
    RASTER_INDEX_ATTRIBUTE = _raster_index
    TILESIZE_OR_NUMTILES = Number of Tiles
    TILE_COLUMN_ATTRIBUTE = _tile_column
    TILE_ROW_ATTRIBUTE = _tile_row
    TILES -> mns_10x10_tiles (writer POSTGIS_RASTER_2)
mns_10x10_tiles (writer POSTGIS_RASTER_2)
    attributes: _raster_index int8, _tile_column int8, _tile_row int8, _num_tile_columns int8, _num_tile_rows int8
Logger_4
    LOG_FEATURE = LOG_ONLY
    MAXCOORDS = 20
    MAXFEATS = 20
    MESSAGE = Feature is:
    SEVERITY = INFO
Note: Créer des tuiles pour chaque niveau de zoom d'une application web
WebMapTiler
    INTERPOLATION_TYPE_NAME = Nearest Neighbor
    MAX_ZOOM_LEVEL = 14
    MIN_ZOOM_LEVEL = 9
    NUM_TILES_ATTRIBUTE = _num_tiles
    QUADKEY_ATTRIBUTE = _quadkey
    RASTER_INDEX_ATTRIBUTE = _raster_index
    TILE_COLUMN_ATTRIBUTE = _tile_column
    TILE_ROW_ATTRIBUTE = _tile_row
    TILE_SCHEME = GoogleMapsCompatible
    ZOOM_LEVEL_ATTRIBUTE = _zoom_level
    TILES -> mns_wmt (writer POSTGIS_RASTER_2)
mns_wmt (writer POSTGIS_RASTER_2)
    attributes: _num_tiles numeric(20,0), _quadkey text, _raster_index numeric(20,0), _tile_column numeric(20,0), _tile_row numeric(20,0), _zoom_level numeric(20,0)
Note: Ombrage
RasterHillshader
    ALGORITHM = Horn
    ALTITUDE = 45
    AZIMUTH = 315
    INTERPOLATE_NODATA = Yes
    -> mns_hillshade (writer POSTGIS_RASTER_2)
    <REJECTED> -> Logger_5
mns_hillshade (writer POSTGIS_RASTER_2)
Logger_5
    LOG_FEATURE = LOG_ONLY
    MAXCOORDS = 20
    MAXFEATS = 20
    MESSAGE = Feature is:
    SEVERITY = INFO

Bookmark: Ilots de chaleur
Note: -- to 3857
Reprojector
    DEST = EPSG:3857
    INTERPOLATION_TYPE_NAME = Nearest Neighbor
    RASTER_CELL_SIZE = Preserve Cells
    RASTER_TOLERANCE = 0.0
    REPROJECTED -> RasterToPolygonCoercer
    REPROJECTED -> RasterSharpener
    REPROJECTED -> RasterCellCoercer
Note: Transforme le raster en polygones
RasterToPolygonCoercer
    EXTRACT_NODATA = No
    LABEL_ATTRIBUTE = _label
    PRESERVE_ATTRIBUTES = Yes
    POLYGONS -> ilots_chaleur_polygones (writer POSTGIS_1)
ilots_chaleur_polygones (writer POSTGIS_1)
    attributes: _label text
Note: Améliore la définition du raster
RasterSharpener
    PRESERVE_BAND_INTERPRETATION = No
    SHARPENING_FACTOR = 3.0
    SHARPENING_FILTER_MODE = Fine
    SHARPENING_ITERATIONS = 5
    SHARPENED -> RasterCellValueRounder
Note: Simplifie la classifcation
RasterCellValueRounder
    PLACES = 1
    ROUND_TYPE = nearest
    -> RasterToPolygonCoercer_2
Note: Transforme le raster en polygones
RasterToPolygonCoercer_2
    EXTRACT_NODATA = No
    LABEL_ATTRIBUTE = classification
    PRESERVE_ATTRIBUTES = Yes
    POLYGONS -> ilots_chaleur_sharp_polygones (writer POSTGIS_2)
ilots_chaleur_sharp_polygones (writer POSTGIS_2)
    attributes: classification text
Note: Transforme les pixels en points
RasterCellCoercer
    CELL_GEOMETRY = Points
    EXTRACT_BAND_VALUES_AS = Z Values
    EXTRACT_NODATA = No
    PRESERVE_ATTRIBUTES = Yes
    -> ilots_chaleur_points (writer POSTGIS_3)
ilots_chaleur_points (writer POSTGIS_3)
Note: On extrait les métadonnées pour en savoir plus
RasterPropertyExtractor_2
    -> RasterPropertyExtractor_2_Output
RasterPropertyExtractor_2_Output: Logger
    LOG_FEATURE = LOG_ONLY
    MAXCOORDS = 20
    MAXFEATS = 20
    MESSAGE = Feature is:
    SEVERITY = INFO

Bookmark: Image aérienne Ville Marie 2002
Note: vers 3857
Reprojector_3
    DEST = EPSG:3857
    INTERPOLATION_TYPE_NAME = Nearest Neighbor
    RASTER_CELL_SIZE = Preserve Cells
    RASTER_TOLERANCE = 0.0
    REPROJECTED -> RasterResampler
Note: Réduction de la taille du raster pour stockage in memory
RasterResampler
    COLUMNS = 1672
    INTERPOLATION_TYPE_NAME = Nearest Neighbor
    ROWCOL_OR_CELLSIZE = RowsColumns
    ROWS = 1711
    RESAMPLED -> hm-2002-can-4000-0257 (writer POSTGIS_RASTER_1)
    RESAMPLED -> RasterPyramider
    RESAMPLED -> WebMapTiler_2
    <REJECTED> -> Logger
Note: Génère des images de taille plus petite pour affichage en fonction des niveaux de zoom si on veut l'afficher dans une application
RasterPyramider
    INTERPOLATION_TYPE_NAME = Nearest Neighbor
    NUMBER_OF_LEVELS = 10
    NUM_PYRAMID_LEVELS_ATTRIBUTE = _num_pyramid_levels
    PYRAMID_LEVEL_ATTRIBUTE = _pyramid_level
    RASTER_INDEX_ATTRIBUTE = _raster_index
    SMALLESTSIZE_OR_NUMLEVELS = Number of Levels
    USE_POWERS_OF_TWO = No
    PYRAMIDS -> FeatureWriter [Tiles]
    <REJECTED> -> Logger_3
SQLExecutor
    COMBINE_ATTRS = Result Attributes Only
    COMBINE_GEOM = Initiator Geometry Only
    DATASET = GEO7630
    FORMAT = POSTGIS
    POSTGIS_CREATE_FEATURE_TABLES_FROM_DATA = Yes
    POSTGIS_DISABLE_COLLECTION_SPLITTING = yes
    POSTGIS_NAMED_CONNECTION = GEO7630
    POSTGIS_QUERY_FEATURE_TYPES_FOR_MERGE_FILTERS = Yes
    POSTGIS_READ_TIME_WITH_TIMEZONE = Yes
    POSTGIS_USE_TRUE_POSTGIS_TYPES = yes
    SQL_STATEMENT = create table geo7630.mns_pyramid_2 as select * from geo7630."hm-2002-can-4000-0257_pyramide" hcp where "_pyramid_level" = 2
Logger_3
    LOG_FEATURE = LOG_ONLY
    MAXCOORDS = 20
    MAXFEATS = 20
    MESSAGE = Feature is:
    SEVERITY = INFO
hm-2002-can-4000-0257 (writer POSTGIS_RASTER_1)
Note: Génère les tuiles pour les application web automatiquement
WebMapTiler_2
    INTERPOLATION_TYPE_NAME = Nearest Neighbor
    NUM_TILES_ATTRIBUTE = _num_tiles
    QUADKEY_ATTRIBUTE = _quadkey
    RASTER_INDEX_ATTRIBUTE = _raster_index
    TILE_COLUMN_ATTRIBUTE = _tile_column
    TILE_NUM_COLUMNS = 256
    TILE_NUM_ROWS = 256
    TILE_ROW_ATTRIBUTE = _tile_row
    TILE_SCHEME = GoogleMapsCompatible
    ZOOM_LEVEL_ATTRIBUTE = _zoom_level
    TILES -> hm-2002-can-4000-0257_wmt (writer POSTGIS_RASTER_3)
hm-2002-can-4000-0257_wmt (writer POSTGIS_RASTER_3)
    attributes: _num_tiles numeric(20,0), _quadkey text, _raster_index numeric(20,0), _tile_column numeric(20,0), _tile_row numeric(20,0), _zoom_level numeric(20,0)
Note: Extraction des métadonnées du raster
RasterPropertyExtractor
    <REJECTED> -> Logger_2

Bookmark: Écris les pyramides en BD
FeatureWriter
    DATASET = GEO7630
    DATASET_ATTR = _dataset
    FEATURE_TYPE_LIST_ATTR = _feature_types
    FORMAT = POSTGIS_RASTER
    POSTGIS_RASTER_BULK_COPY = YES
    POSTGIS_RASTER_COORDINATE_SYSTEM_GRANULARITY = FEATURE_TYPE
    POSTGIS_RASTER_LOWERCASE_ATTRIBUTE_NAMES = Yes
    POSTGIS_RASTER_NAMED_CONNECTION = GEO7630
    POSTGIS_RASTER_SPATIAL_COLUMN_NAME = rast
    POSTGIS_RASTER_START_TRANSACTION = 0
    POSTGIS_RASTER_STRICT_TEMPORAL_TYPE_HANDLING = Yes
    POSTGIS_RASTER_TRANSACTION_INTERVAL = 100
    TOTAL_FEATURES_WRITTEN_ATTR = _total_features_written
    SUMMARY -> SQLExecutor [INITIATOR]
