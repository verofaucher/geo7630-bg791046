FME workspace Lab3.fmw

Parameters:
- DestDataset_GEOJSON =
- SourceDataset_CSV2_2 =
- SourceDataset_GEOJSON =
- SourceDataset_GEOTIFF =
- SourceDataset_LAS =
- SourceDataset_LAS_10 =
- SourceDataset_LAS_11 =
- SourceDataset_LAS_7 =
- SourceDataset_LAS_8 =
- SourceDataset_LAS_9 =
- SourceDataset_PNGRASTER =
- SourceDataset_PNGRASTER_3 =
- SourceDataset_SHAPEFILE =
- SourceDataset_SHAPEFILE_3 =

Readers:
- LAS_1: LAS from $(SourceDataset_LAS)
- LAS_2: LAS from $(SourceDataset_LAS_9)
- LAS_3: LAS from $(SourceDataset_LAS_7)
- LAS_4: LAS from $(SourceDataset_LAS_11)
- CSV2_1: CSV2 from $(SourceDataset_CSV2_2)
- PNGRASTER_1: PNGRASTER from $(SourceDataset_PNGRASTER) in EPSG:3857
- GEOTIFF_1: GEOTIFF from $(SourceDataset_GEOTIFF) in EPSG:2950
- LAS_5: LAS from $(SourceDataset_LAS_8)
- LAS_6: LAS from $(SourceDataset_LAS_10)
- GEOJSON_1: GEOJSON from $(SourceDataset_GEOJSON)
- PNGRASTER_2: PNGRASTER from $(SourceDataset_PNGRASTER_3)
- SHAPEFILE_1: SHAPEFILE from $(SourceDataset_SHAPEFILE)
- SHAPEFILE_2: SHAPEFILE from $(SourceDataset_SHAPEFILE_3)

Writers:
- GEOJSON_2: GEOJSON to $(DestDataset_GEOJSON)

CSV (reader CSV2_1) [off]
    attributes: id uint32, data_urls varchar(81)
    -> AttributeFilter_2
    -> AttributeFilter_3
    -> AttributeFilter_4
    -> AttributeFilter_5
    -> AttributeFilter_6
    -> AttributeFilter_7
GEOTIFF (reader GEOTIFF_1) [off]
    -> RasterPropertyExtractor
PointCloudPropertyExtractor
    CALCULATE_EXTENTS_DISPLAY = No
    POINT_COMPONENTS = x   MINMAX y   MINMAX z   MINMAX
Note: Très gourmant en computing power, mais préserve la shape du nuage
PointCloudSimplifier [off]
    MASB_BISECT_K = 2
    MASB_BISECT_T = 1.0
    MASB_CELLSIZE = Auto
    MASB_D_PLANAR_T = 32.0
    MASB_D_PRESERVE_T = 20.0
    MASB_EPSILON = 0.5
    MASB_INTERIOR = Use Interior and Exterior MAT
    MASB_IR = Auto
    MASB_K = 10
    MASB_MAX_DENSITY = None
    MASB_MIN_DENSITY = None
    MASB_SQUARED = Linear
    SIMPLIFIER_TYPE_DISPLAY = Medial Axis Transform
    SIMPLIFIED -> PointCloudOnRasterComponentSetter [PointCloud]
    SIMPLIFIED -> PointCloudPropertyExtractor_3
    REMOVED -> PointCloudSimplifier_Removed
PointCloudPropertyExtractor_3
    CALCULATE_EXTENTS_DISPLAY = No
    POINT_COMPONENTS = x   MINMAX y   MINMAX z   MINMAX
PointCloudPropertyExtractor_4
    CALCULATE_EXTENTS_DISPLAY = No
    POINT_COMPONENTS = x   MINMAX y   MINMAX z   MINMAX
PointCloudCoercer__Rejected_: Logger
    LOG_FEATURE = LOG_ONLY
    MAXCOORDS = 20
    MAXFEATS = 20
    MESSAGE = Feature is:
    SEVERITY = INFO
Clipper_2__Rejected_: Logger
    LOG_FEATURE = LOG_ONLY
    MAXCOORDS = 20
    MAXFEATS = 20
    MESSAGE = Feature is:
    SEVERITY = INFO
ExportGeoJSON (writer GEOJSON_2)
    attributes: _output_color string, z float
PointOnAreaOverlayer_2__Rejected_: Logger
    LOG_FEATURE = LOG_ONLY
    MAXCOORDS = 20
    MAXFEATS = 20
    MESSAGE = Feature is:
    SEVERITY = INFO

Bookmark: Raster downloader, resampler and mosaicker , not working because rasters are not georeferenced
AttributeFilter_2 [off]
    ATTR_NAME = id
    ATTR_VALUES = <Empty>,<Missing>,<Null>,<Unfiltered>,1
    1 -> FeatureReader_6 [INITIATOR] [off]
FeatureReader_6 [off]
    ATTR_ACCUM_MODE = Only Use Result
    CACHE_TIMEOUT_HRS = 24
    COMBINE_GEOM = Use Result
    DATASET = @Value(data_urls)
    FORMAT = TIFF
    INTERACT = NONE
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterPropertyExtractor_8 [off]
RasterPropertyExtractor_8 [off]
    -> RasterResampler_5 [off]
RasterResampler_5 [off]
    COLUMNS = @Value(_num_columns)/10
    INTERPOLATION_TYPE_NAME = Nearest Neighbor
    ROWCOL_OR_CELLSIZE = RowsColumns
    ROWS = @Value(_num_rows)/10
    RESAMPLED -> RasterMosaicker_2
AttributeFilter_3 [off]
    ATTR_NAME = id
    ATTR_VALUES = <Empty>,<Missing>,<Null>,<Unfiltered>,2
    2 -> FeatureReader [INITIATOR] [off]
FeatureReader [off]
    ATTR_ACCUM_MODE = Only Use Result
    CACHE_TIMEOUT_HRS = 24
    COMBINE_GEOM = Use Result
    DATASET = @Value(data_urls)
    FORMAT = TIFF
    INTERACT = NONE
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterPropertyExtractor_7 [off]
RasterPropertyExtractor_7 [off]
    -> RasterResampler_4 [off]
RasterResampler_4 [off]
    COLUMNS = @Value(_num_columns)/10
    INTERPOLATION_TYPE_NAME = Nearest Neighbor
    ROWCOL_OR_CELLSIZE = RowsColumns
    ROWS = @Value(_num_rows)/10
    RESAMPLED -> RasterMosaicker_2 [off]
AttributeFilter_4 [off]
    ATTR_NAME = id
    ATTR_VALUES = <Empty>,<Missing>,<Null>,<Unfiltered>,3
    3 -> FeatureReader_2 [INITIATOR] [off]
FeatureReader_2 [off]
    ATTR_ACCUM_MODE = Only Use Result
    CACHE_TIMEOUT_HRS = 24
    COMBINE_GEOM = Use Result
    DATASET = @Value(data_urls)
    FORMAT = TIFF
    INTERACT = NONE
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterPropertyExtractor_3 [off]
RasterPropertyExtractor_3 [off]
    -> RasterResampler_3 [off]
RasterResampler_3 [off]
    COLUMNS = @Value(_num_columns)/10
    INTERPOLATION_TYPE_NAME = Nearest Neighbor
    ROWCOL_OR_CELLSIZE = RowsColumns
    ROWS = @Value(_num_rows)/10
    RESAMPLED -> RasterMosaicker_2
AttributeFilter_5 [off]
    ATTR_NAME = id
    ATTR_VALUES = <Empty>,<Missing>,<Null>,<Unfiltered>,4
    4 -> FeatureReader_3 [INITIATOR] [off]
FeatureReader_3 [off]
    ATTR_ACCUM_MODE = Only Use Result
    CACHE_TIMEOUT_HRS = 24
    COMBINE_GEOM = Use Result
    DATASET = @Value(data_urls)
    FORMAT = TIFF
    INTERACT = NONE
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterPropertyExtractor_4 [off]
    <REJECTED> -> FeatureReader_3__Rejected_ [off]
RasterPropertyExtractor_4 [off]
    -> RasterResampler_6 [off]
RasterResampler_6 [off]
    COLUMNS = @Value(_num_columns)/10
    INTERPOLATION_TYPE_NAME = Nearest Neighbor
    ROWCOL_OR_CELLSIZE = RowsColumns
    ROWS = @Value(_num_rows)/10
    RESAMPLED -> RasterMosaicker_2
FeatureReader_3__Rejected_: Logger [off]
    LOG_FEATURE = LOG_ONLY
    MAXCOORDS = 20
    MAXFEATS = 20
    MESSAGE = Feature is:
    SEVERITY = INFO
AttributeFilter_6 [off]
    ATTR_NAME = id
    ATTR_VALUES = <Empty>,<Missing>,<Null>,<Unfiltered>,5
    5 -> FeatureReader_4 [INITIATOR] [off]
FeatureReader_4 [off]
    ATTR_ACCUM_MODE = Only Use Result
    CACHE_TIMEOUT_HRS = 24
    COMBINE_GEOM = Use Result
    DATASET = @Value(data_urls)
    FORMAT = TIFF
    INTERACT = NONE
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterPropertyExtractor_5 [off]
RasterPropertyExtractor_5 [off]
    -> RasterPropertyExtractor_9 [off]
RasterPropertyExtractor_9 [off]
    -> RasterMosaicker_2
AttributeFilter_7 [off]
    ATTR_NAME = id
    ATTR_VALUES = <Empty>,<Missing>,<Null>,<Unfiltered>,6
    6 -> FeatureReader_5 [INITIATOR] [off]
FeatureReader_5 [off]
    ATTR_ACCUM_MODE = Only Use Result
    CACHE_TIMEOUT_HRS = 24
    COMBINE_GEOM = Use Result
    DATASET = @Value(data_urls)
    FORMAT = TIFF
    INTERACT = NONE
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterPropertyExtractor_6 [off]
RasterPropertyExtractor_6 [off]
    -> RasterPropertyExtractor_10 [off]
RasterPropertyExtractor_10 [off]
    -> RasterMosaicker_2
RasterMosaicker_2 [off]
    ACCUM_ATTRS_NAME = Use Attributes From One Feature
    INTERPOLATION_TYPE_NAME = Nearest Neighbor
    MERGE_PALETTES_NAME = No
    NODATA_OVERWRITE = No
    OVERLAPPING_VALUES = last
    SNAPPING_TYPE_NAME = Resample

Bookmark: Extract Ile Ste-Helene Polygon frpm MNS
RasterPropertyExtractor [off]
    -> RasterResampler
RasterResampler [off]
    COLUMNS = @Value(_num_columns)/10
    INTERPOLATION_TYPE_NAME = Nearest Neighbor
    ROWCOL_OR_CELLSIZE = RowsColumns
    ROWS = @Value(_num_rows)/10
    RESAMPLED -> ContourGenerator [POINTS/LINES]
    <REJECTED> -> RasterResampler__Rejected_
ContourGenerator [off]
    CONTOUR_DIMENSION = 2
    CONTOUR_INTERVAL = 10
    ELEV_ATTR = _elevation
    IGNORE_INPUT_ON_INTERVAL = Remove Input Points On Contour Interval
    TOLERANCE = 1
    CONTOURS -> AreaBuilder
    <REJECTED> -> ContourGenerator__Rejected_
AreaBuilder [off]
    ALLOW_CYCLES = No
    CHECK_CURVE_DIRECTION = No
    CONNECT_Z_MODE = First Wins
    CONSIDER_NODE_ELEVATION = no
    DEAGGREGATE_INPUT = Deaggregate
    DONUT_CREATION = Yes
    DROP_HOLES = No
    LINES_AS_SEGMENTS = No
    POLY_ACCUM_ATTRS_NAME = Use Attributes From One Feature
    POLY_DIRECTION = _direction
    POLY_LIST_ATTRS_TO_INCLUDE_MODE = Selected Attributes
    SNAPTYPE_PARAM = None
    SNAP_TOLERANCE = 0
    AREA -> Dissolver
    <REJECTED> -> AreaBuilder__Rejected_
Dissolver [off]
    ACCUM_INPUT_ATTRS = Use Attributes From One Feature
    CLEANING_TOLERANCE = Automatic
    CONNECT_Z_MODE = First Wins
    DEAGGREGATE_INPUT = Yes
    AREA -> PointOnAreaOverlayer [AREA]
    <REJECTED> -> Dissolver__Rejected_
Dissolver__Rejected_: Logger [off]
    LOG_FEATURE = LOG_ONLY
    MAXCOORDS = 20
    MAXFEATS = 20
    MESSAGE = Feature is:
    SEVERITY = INFO
AreaBuilder__Rejected_: Logger [off]
    LOG_FEATURE = LOG_ONLY
    MAXCOORDS = 20
    MAXFEATS = 20
    MESSAGE = Feature is:
    SEVERITY = INFO
ContourGenerator__Rejected_: Logger [off]
    LOG_FEATURE = LOG_ONLY
    MAXCOORDS = 20
    MAXFEATS = 20
    MESSAGE = Feature is:
    SEVERITY = INFO
RasterResampler__Rejected_: Logger [off]
    LOG_FEATURE = LOG_ONLY
    MAXCOORDS = 20
    MAXFEATS = 20
    MESSAGE = Feature is:
    SEVERITY = INFO
Note: x 302118.6079 y 5042102.8750
Creator [off]
    GEOM = <?xml version="1.0" encoding="US_ASCII" standalone="no" ?><geometry><point><coord x="302118.6079" y="5042102.875"/></point></geometry>
    GEOMTYPE = Geometry Object
    NUM = 1
    CREATED -> Reprojector
Reprojector [off]
    DEST = EPSG:2950
    INTERPOLATION_TYPE_NAME = Nearest Neighbor
    RASTER_CELL_SIZE = Preserve Cells
    RASTER_TOLERANCE = 0.0
    REPROJECTED -> PointOnAreaOverlayer [POINT]
PointOnAreaOverlayer [off]
    DEAGGREGATE_INPUT = Yes
    OV_ATTR = _overlaps
    POLYS_FIRST = YES
    AREA -> AttributeFilter
    <REJECTED> -> PointOnAreaOverlayer__Rejected_
AttributeFilter [off]
    ATTR_NAME = _overlaps
    ATTR_VALUES = <Empty>,0,1,<Missing>,<Null>,<Unfiltered>
PointOnAreaOverlayer__Rejected_: Logger [off]
    LOG_FEATURE = LOG_ONLY
    MAXCOORDS = 20
    MAXFEATS = 20
    MESSAGE = Feature is:
    SEVERITY = INFO

Bookmark: Lecture, resampling combinaison et ESRI Reprojector (2950 to 3857)
LAS (reader LAS_6)
    -> PointCloudThinner_6
PointCloudThinner_6
    INTERVAL = 30
    THINNED -> PointCloudCombiner
    <REJECTED> -> PointCloudThinner_6__Rejected_
PointCloudThinner_6__Rejected_: Logger
    LOG_FEATURE = LOG_ONLY
    MAXCOORDS = 20
    MAXFEATS = 20
    MESSAGE = Feature is:
    SEVERITY = INFO
LAS (reader LAS_5)
    -> PointCloudThinner_5
PointCloudThinner_5
    INTERVAL = 30
    THINNED -> PointCloudCombiner
    <REJECTED> -> PointCloudThinner_5__Rejected_
PointCloudThinner_5__Rejected_: Logger
    LOG_FEATURE = LOG_ONLY
    MAXCOORDS = 20
    MAXFEATS = 20
    MESSAGE = Feature is:
    SEVERITY = INFO
LAS (reader LAS_4)
    -> PointCloudThinner_4
PointCloudThinner_4
    INTERVAL = 30
    THINNED -> PointCloudCombiner
    <REJECTED> -> PointCloudThinner_4__Rejected_
PointCloudThinner_4__Rejected_: Logger
    LOG_FEATURE = LOG_ONLY
    MAXCOORDS = 20
    MAXFEATS = 20
    MESSAGE = Feature is:
    SEVERITY = INFO
LAS (reader LAS_2)
    -> PointCloudThinner
PointCloudThinner
    INTERVAL = 30
    THINNED -> PointCloudPropertyExtractor
    THINNED -> PointCloudCombiner
    <REJECTED> -> PointCloudThinner__Rejected_
PointCloudThinner__Rejected_: Logger
    LOG_FEATURE = LOG_ONLY
    MAXCOORDS = 20
    MAXFEATS = 20
    MESSAGE = Feature is:
    SEVERITY = INFO
LAS (reader LAS_1)
    -> PointCloudThinner_2
PointCloudThinner_2
    INTERVAL = 30
    THINNED -> PointCloudCombiner
    <REJECTED> -> PointCloudThinner_2__Rejected_
PointCloudThinner_2__Rejected_: Logger
    LOG_FEATURE = LOG_ONLY
    MAXCOORDS = 20
    MAXFEATS = 20
    MESSAGE = Feature is:
    SEVERITY = INFO
LAS (reader LAS_3)
    -> PointCloudThinner_3
PointCloudThinner_3
    INTERVAL = 30
    THINNED -> PointCloudCombiner
    <REJECTED> -> PointCloudThinner_3__Rejected_
Note: Combine tous les nuages en un seul nuage
PointCloudCombiner
    ACCUM_ATTRS_NAME = Yes
    EXTRACT_RASTER_NODATA_NAME = No
    SPACING = 1.0
    -> EsriReprojector_6
Note: Reprojette du 2950 en 3857 le reprojector normal ne le fait pas
EsriReprojector_6
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_DIRECTION = Forward
    GEOTRANSFORMATION_NAME = NAD_1983_CSRS_To_WGS_1984
    INTERPOLATION_TYPE_NAME = Nearest Neighbor
    RASTER_CELL_SIZE = Preserve Cells
    RASTER_TOLERANCE = 0.0
    SOURCE = ESRIWKT|NAD_1983_CSRS_MTM_8|PROJCS["NAD_1983_CSRS_MTM_8",GEOGCS["GCS_North_American_1983_CSRS",DATUM["D_North_American_1983_CSRS",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    REPROJECTED -> Clipper [CLIPPEE]
PointCloudThinner_3__Rejected_: Logger
    LOG_FEATURE = LOG_ONLY
    MAXCOORDS = 20
    MAXFEATS = 20
    MESSAGE = Feature is:
    SEVERITY = INFO

Bookmark: Lecture et reprojection de la limite terrestre
limites-terrestres (reader GEOJSON_1)
    attributes: DefaultAtt string
    -> Reprojector_3
Reprojector_3
    DEST = EPSG:3857
    INTERPOLATION_TYPE_NAME = Nearest Neighbor
    RASTER_CELL_SIZE = Preserve Cells
    RASTER_TOLERANCE = 0.0
    SOURCE = EPSG:4326
    REPROJECTED -> Clipper [CLIPPER]

Bookmark: Découpe et simplifie le nuage de points combiné avec la limette terrestre
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> PointCloudPropertyExtractor_4
    INSIDE -> PointCloudSimplifier
    INSIDE -> PointCloudThinner_7
PointCloudSimplifier_Removed: Logger
    LOG_FEATURE = LOG_ONLY
    MAXCOORDS = 20
    MAXFEATS = 20
    MESSAGE = Feature is:
    SEVERITY = INFO
PointCloudThinner_7
    INTERVAL = 5
    THINNED -> PointCloudOnRasterComponentSetter [PointCloud]

Bookmark: Image
Note: Image prise screenshot de google earth en 4 shots, puis géoréférencée.
PNGRASTER (reader PNGRASTER_2)
    -> Reprojector_2
Reprojector_2
    DEST = EPSG:32188
    INTERPOLATION_TYPE_NAME = Nearest Neighbor
    RASTER_CELL_SIZE = Preserve Cells
    RASTER_TOLERANCE = 0.0
    SOURCE = EPSG:3857
    REPROJECTED -> RasterMosaicker
Note: Combinaison des images
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> RasterSelector
Note: Choix des bandes
RasterSelector
    BAND_LIST = 0:;1:;2:
    SELECTION_MODE = Band and Palette List
    -> EsriReprojector_2
EsriReprojector_2
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_DIRECTION = Forward
    GEOTRANSFORMATION_NAME = NAD_1983_CSRS_To_WGS_1984
    INTERPOLATION_TYPE_NAME = Nearest Neighbor
    RASTER_CELL_SIZE = Preserve Cells
    RASTER_TOLERANCE = 0.0
    SOURCE = ESRIWKT|NAD_1983_CSRS_MTM_8|PROJCS["NAD_1983_CSRS_MTM_8",GEOGCS["GCS_North_American_1983_CSRS",DATUM["D_North_American_1983_CSRS",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    REPROJECTED -> PointCloudOnRasterComponentSetter [Raster]

Bookmark: Association du raster (couleur) vers les points non colorisés
Note: Permet de joindre les informations d'un raster avec un nuage de points
PointCloudOnRasterComponentSetter
    COMPONENT_SPECIFICATION = Color
    DEFAULT_VALUES_OVERWRITE_DATA = No
    EXTRACT_NODATA = No
    INTERPOLATION = Nearest Neighbor
    PointCloud -> PointCloudCombiner_2
    <REJECTED> -> PointCloudOnRasterComponentSetter__Rejected_
Note: Recombine les nuages en 1 seul
PointCloudCombiner_2
    ACCUM_ATTRS_NAME = Yes
    EXTRACT_RASTER_NODATA_NAME = No
    SPACING = 1.0
    -> PointCloudFilter
    <REJECTED> -> PointCloudCombiner_2__Rejected_
Note: Essaie de filtre les points qui n'ont pas de valeurs depuis le raster
PointCloudFilter
    FILTER_TABLE = @Component(color_red)!=0&&@Component(color_blue)!=0&&@Component(color_green) @Component(color_red)!=0 && @Component(color_green)!=0  && @Component(color_blue)!=0
    OUTPUT_UNFILTERED_POINTS = Yes
    @Component(color_red)!=0 && @Component(color_green)!=0 && @Component(color_blue)!=0 -> BoundingBoxAccumulator
    @Component(color_red)!=0 && @Component(color_green)!=0 && @Component(color_blue)!=0 -> PointCloudCoercer
    <REJECTED> -> AreaBuilder_3__Rejected_
Note: Transforme le nuage de points en couche vertex de points unique XYZ avec propriétés
PointCloudCoercer
    ACCUM_ATTRS_NAME = Yes
    CONVERT_TO_DISPLAY = Individual Points
    PART_NUMBER_ATTR_NAME = _part_number
    POINT_COMPONENTS = z color_red color_green color_blue
    POINT_COMPONENTS_PRESERVE_DISPLAY = Attributes
    COERCED -> PointOnAreaOverlayer_2 [POINT]
    <REJECTED> -> PointCloudCoercer__Rejected_
AreaBuilder_3__Rejected_: Logger
    LOG_FEATURE = LOG_ONLY
    MAXCOORDS = 20
    MAXFEATS = 20
    MESSAGE = Feature is:
    SEVERITY = INFO
PointCloudCombiner_2__Rejected_: Logger
    LOG_FEATURE = LOG_ONLY
    MAXCOORDS = 20
    MAXFEATS = 20
    MESSAGE = Feature is:
    SEVERITY = INFO
PointCloudOnRasterComponentSetter__Rejected_: Logger
    LOG_FEATURE = LOG_ONLY
    MAXCOORDS = 20
    MAXFEATS = 20
    MESSAGE = Feature is:
    SEVERITY = INFO

Bookmark: Génère un bounding box pour découper les empreintes de batiments à notre espace de travail
Note: BoundingBoxAccumulator
BoundingBoxAccumulator
    ACCUM_ATTRS_NAME = Use Attributes From One Feature
    BOUNDING_BOX -> Clipper_2 [CLIPPER]
    BOUNDING_BOX -> Clipper_4 [CLIPPER]

Bookmark: Lecture et nettoyage des details de toits
CARTO-BAT-DETAIL (reader SHAPEFILE_2)
    attributes: calque varchar(200), projection varchar(200), reference varchar(200), EQM_plani varchar(200), EQM_alti varchar(200), MAJ varchar(200), methode varchar(200), source varchar(200), producteur varchar(200), longueur varchar(200), version varchar(200)
    -> EsriReprojector_5
EsriReprojector_5
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_DIRECTION = Forward
    GEOTRANSFORMATION_NAME = NAD_1983_CSRS_To_WGS_1984
    INTERPOLATION_TYPE_NAME = Nearest Neighbor
    RASTER_CELL_SIZE = Preserve Cells
    RASTER_TOLERANCE = 0.0
    SOURCE = ESRIWKT|NAD_1983_CSRS_MTM_8|PROJCS["NAD_1983_CSRS_MTM_8",GEOGCS["GCS_North_American_1983_CSRS",DATUM["D_North_American_1983_CSRS",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    REPROJECTED -> Clipper_4 [CLIPPEE]
Note: Retire les polygones non nécessaires
Clipper_4
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> PolygonCutter [Lines]
    <REJECTED> -> Clipper_4__Rejected_
Clipper_4__Rejected_: Logger
    LOG_FEATURE = LOG_ONLY
    MAXCOORDS = 20
    MAXFEATS = 20
    MESSAGE = Feature is:
    SEVERITY = INFO

Bookmark: Lecture et nettoyage des emruntes de toits
CARTO-BAT-TOIT (reader SHAPEFILE_1)
    attributes: calque varchar(200), projection varchar(200), reference varchar(200), EQM_plani varchar(200), EQM_alti varchar(200), MAJ varchar(200), methode varchar(200), source varchar(200), producteur varchar(200), superficie varchar(200), version varchar(200)
    -> EsriReprojector_4
EsriReprojector_4
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_DIRECTION = Forward
    GEOTRANSFORMATION_NAME = NAD_1983_CSRS_To_WGS_1984
    INTERPOLATION_TYPE_NAME = Nearest Neighbor
    RASTER_CELL_SIZE = Preserve Cells
    RASTER_TOLERANCE = 0.0
    SOURCE = ESRIWKT|NAD_1983_CSRS_MTM_8|PROJCS["NAD_1983_CSRS_MTM_8",GEOGCS["GCS_North_American_1983_CSRS",DATUM["D_North_American_1983_CSRS",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    REPROJECTED -> Clipper_2 [CLIPPEE]
Note: Retire les polygones non nécessaires
Clipper_2
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> PolygonCutter [Polygons]
    <REJECTED> -> Clipper_2__Rejected_

Bookmark: Découpe les empruntes de toits avec le détails des toits
PolygonCutter
    DONUTHOLES = Yes
    SNAP_TOLERANCE = 0.001
    Cut -> PointOnAreaOverlayer_2 [AREA]

Bookmark: Jointure spatiale des points et des batiments, calcul du z moyen pour chacune des surfaces de toit et exposition des propriétés pour créer des polygones cartographiables
Note: Jointure spatiale
PointOnAreaOverlayer_2
    CANDIDATE_LIST_ATTRS_TO_INCLUDE_MODE = All Attributes
    CANDIDATE_LIST_NAME = z_accumulation
    DEAGGREGATE_INPUT = Yes
    OV_ATTR = _overlaps
    POLYS_FIRST = YES
    AREA -> ListSummer
    <REJECTED> -> PointOnAreaOverlayer_2__Rejected_
Note: Calcule de la sommes des Z par surface
ListSummer
    RESULT = _sum
    SRC_LIST = z_accumulation{}.z
    -> AttributeCreator
Note: Calcul de la moyenne du Z par count de points dans polygone
AttributeCreator
    ATTR_TABLE = SET_TO z = @Evaluate(@round(@Value(_sum)/@Value(_overlaps),4))
    -> AttributeManager
Note: Nettoyage
AttributeManager
    ATTR_TABLE:
      REMOVE calque
      REMOVE projection
      REMOVE reference
      REMOVE EQM_plani
      REMOVE EQM_alti
      REMOVE MAJ
      REMOVE methode
      REMOVE source
      REMOVE producteur
      REMOVE superficie
      REMOVE version
      REMOVE _clipped
      REMOVE _overlaps
      REMOVE _sum
      REMOVE z_accumulation{}.z
      REMOVE _group_by
      REMOVE z_accumulation{}.fme_basename
      REMOVE z_accumulation{}._clipped
      SET_TO z_accumulation{}.fme_color = @Value(z_accumulation{1}.fme_color)
      REMOVE z_accumulation{}._part_number
    USER_EXPOSED_ATTRIBUTES = newValue,test2{}.z,longueur
    -> ColorConverter
Note: Conversion des couleurs FME vers RGB ou HEX
ColorConverter
    InputAttribute = z_accumulation{1}.fme_color
    InputModel = FME
    OutputModel = Web RGB
    -> ExportGeoJSON (writer GEOJSON_2)

FME custom transformer ColorConverter
Converts color values between different formats (FME
 RGB
 Web RGB and CMYK)
Input:
1 attribute containing a color triplet in either FME, RGB, Web RGB or CMYK format, comma-separated
Output:
Attributes _output_color (full color triplet in the required format), _output_red, output_green and _output_blue
Supported color models:
FME color, RGB values in range 0..1
RGB values in range 0..255
Web RGB values, a hexadecimal string of 6 characters containing an RGB triplet with each value in the range 00..FF
CMYK values in range 0..1 and 0..100
Note that due to rounding errors the resulting colors might be a bit off. Especially any conversions between the RGB and CMYK color spaces might yield results that differ from other applications (since the RGB and CMYK color spaces are slightly different)

Parameters:
- InputAttribute =
- InputModel =
- OutputModel =

Input (input)
    -> TestFilter
Note: Select input color model
TestFilter
    DEFAULT_VALUE = <UNFILTERED>
    TEST_LIST = BOOL_OP,OR,COMPOSITE_TEST,<Unused>,TEST_CLAUSE,"TEST $(InputModel) = FME",FME,BOOL_OP,OR,COMPOSITE_TEST,<Unused>,TEST_CLAUSE,"TEST $(InputModel) = RGB",RGB,BOOL_OP,OR,COMPOSITE_TEST,<Unused>,TEST_CLAUSE,"TEST $(InputModel) = Web RGB",Web RGB,BOOL_OP,OR,COMPOSITE_TEST,<Unused>,TEST_CLAUSE,"TEST $(InputModel) = CMYK (0..100)",CMYK (0..100),BOOL_OP,OR,COMPOSITE_TEST,<Unused>,TEST_CLAUSE,"TEST $(InputModel) = CMYK (0..1)",CMYK (0..1)
    FME -> AttributeSplitter
    RGB -> AttributeSplitter_2
    Web RGB -> StringReplacer
    CMYK (0..100) -> AttributeSplitter_5
    CMYK (0..1) -> AttributeSplitter_4
Note: Select output color model
TestFilter_2
    DEFAULT_VALUE = <UNFILTERED>
    TEST_LIST = BOOL_OP,OR,COMPOSITE_TEST,<Unused>,TEST_CLAUSE,"TEST $(OutputModel) = FME",FME,BOOL_OP,OR,COMPOSITE_TEST,<Unused>,TEST_CLAUSE,"TEST $(OutputModel) = RGB",RGB,BOOL_OP,OR,COMPOSITE_TEST,<Unused>,TEST_CLAUSE,"TEST $(OutputModel) = Web RGB",Web RGB,BOOL_OP,OR,COMPOSITE_TEST,<Unused>,TEST_CLAUSE,"TEST $(OutputModel) = CMYK (0..1)",CMYK (0..1),BOOL_OP,OR,COMPOSITE_TEST,<Unused>,TEST_CLAUSE,"TEST $(OutputModel) = CMYK (0..100)",CMYK (0..100)
    FME -> AttributeManager_5
    RGB -> AttributeManager_2
    Web RGB -> AttributeManager_7
    CMYK (0..1) -> AttributeManager_10
    CMYK (0..100) -> AttributeManager_11
Output (output)

Bookmark: FME color triplet
AttributeSplitter
    ATTR_NAME = $(InputAttribute)
    DELIMITER = ,
    DROP_EMPTY_PARTS = No
    LIST_NAME = _list
    TRIM_OPTION = Both
    -> AttributeManager
AttributeManager
    ATTR_TABLE:
      SET_TO _input_red = @Value(_list{0})
      SET_TO _input_green = @Value(_list{1})
      SET_TO _input_blue = @Value(_list{2})
    -> TestFilter_2

Bookmark: RGB color triplet
AttributeSplitter_2
    ATTR_NAME = $(InputAttribute)
    DELIMITER = ,
    DROP_EMPTY_PARTS = No
    LIST_NAME = _list
    TRIM_OPTION = Both
    -> AttributeManager_3
AttributeManager_3
    ATTR_TABLE:
      SET_TO _input_red = @Evaluate(@Value(_list{0})/255)
      SET_TO _input_green = @Evaluate(@Value(_list{1})/255)
      SET_TO _input_blue = @Evaluate(@Value(_list{2})/255)
    -> TestFilter_2

Bookmark: Web RGB (hexadecimal)
StringReplacer
    CASE = NO
    FIND_TEXT = ^#
    NO_MATCH = _FME_NO_OP_
    REGEXP = YES
    SRC_ATTRS = $(InputAttribute)
    -> AttributeSplitter_3
AttributeSplitter_3
    ATTR_NAME = $(InputAttribute)
    DELIMITER = 2s2s2s
    DROP_EMPTY_PARTS = No
    LIST_NAME = _list
    TRIM_OPTION = Both
    -> BaseConverter
BaseConverter
    DBASE = 10
    OBASE = 16
    SRC = _list{0}
    VAL_ATTR = _input_red
    WIDTH = 3
    -> BaseConverter_2
BaseConverter_2
    DBASE = 10
    OBASE = 16
    SRC = _list{1}
    VAL_ATTR = _input_green
    WIDTH = 3
    -> BaseConverter_3
BaseConverter_3
    DBASE = 10
    OBASE = 16
    SRC = _list{2}
    VAL_ATTR = _input_blue
    WIDTH = 3
    -> AttributeManager_4
AttributeManager_4
    ATTR_TABLE:
      SET_TO _input_red = @Evaluate(@Value(_input_red)/255)
      SET_TO _input_green = @Evaluate(@Value(_input_green)/255)
      SET_TO _input_blue = @Evaluate(@Value(_input_blue)/255)
    -> TestFilter_2

Bookmark: CMYK
AttributeSplitter_5
    ATTR_NAME = $(InputAttribute)
    DELIMITER = ,
    DROP_EMPTY_PARTS = No
    LIST_NAME = _list
    TRIM_OPTION = Both
    -> AttributeManager_9
AttributeManager_9
    ATTR_TABLE:
      SET_TO _input_red = @Evaluate((1-(@Value(_list{0})/100))*(1-(@Value(_list{3})/100)))
      SET_TO _input_green = @Evaluate((1-(@Value(_list{1})/100))*(1-(@Value(_list{3})/100)))
      SET_TO _input_blue = @Evaluate((1-(@Value(_list{2})/100))*(1-(@Value(_list{3})/100)))
    -> TestFilter_2
AttributeSplitter_4
    ATTR_NAME = $(InputAttribute)
    DELIMITER = ,
    DROP_EMPTY_PARTS = No
    LIST_NAME = _list
    TRIM_OPTION = Both
    -> AttributeManager_8
AttributeManager_8
    ATTR_TABLE:
      SET_TO _input_red = @Evaluate((1-@Value(_list{0}))*(1-@Value(_list{3})))
      SET_TO _input_green = @Evaluate((1-@Value(_list{1}))*(1-@Value(_list{3})))
      SET_TO _input_blue = @Evaluate((1-@Value(_list{2}))*(1-@Value(_list{3})))
    -> TestFilter_2

Bookmark: FME color triplet
AttributeManager_5
    ATTR_TABLE:
      RENAME_SET_VALUE _input_red > _output_red
      RENAME_SET_VALUE _input_green > _output_green
      RENAME_SET_VALUE _input_blue > _output_blue
      SET_TO _output_color = @Value(_output_red),@Value(_output_green),@Value(_output_blue)
    -> Output (output)

Bookmark: RGB color triplet
AttributeManager_2
    ATTR_TABLE:
      SET_TO _output_red = @Evaluate(@int(@Value(_input_red)*255))
      SET_TO _output_green = @Evaluate(@int(@Value(_input_green)*255))
      SET_TO _output_blue = @Evaluate(@int(@Value(_input_blue)*255))
      SET_TO _output_color = @Value(_output_red),@Value(_output_green),@Value(_output_blue)
    -> Output (output)

Bookmark: Web RGB (hexadecimal
AttributeManager_7
    ATTR_TABLE:
      SET_TO _input_red = @Evaluate(int(@Value(_input_red)*255))
      SET_TO _input_green = @Evaluate(int(@Value(_input_green)*255))
      SET_TO _input_blue = @Evaluate(int(@Value(_input_blue)*255))
    -> BaseConverter_4
    -> AttributeManager_7_Output
BaseConverter_4
    DBASE = 16
    OBASE = 10
    SRC = _input_red
    VAL_ATTR = _output_red
    WIDTH = 2
    -> BaseConverter_5
BaseConverter_5
    DBASE = 16
    OBASE = 10
    SRC = _input_green
    VAL_ATTR = _output_green
    WIDTH = 2
    -> BaseConverter_6
BaseConverter_6
    DBASE = 16
    OBASE = 10
    SRC = _input_blue
    VAL_ATTR = _output_blue
    WIDTH = 2
    -> AttributeManager_6
AttributeManager_6
    ATTR_TABLE = SET_TO _output_color = #@Value(_output_red)@Value(_output_green)@Value(_output_blue)
    -> Output (output)
AttributeManager_7_Output: Inspector

Bookmark: CMYK
AttributeManager_10
    ATTR_TABLE:
      SET_TO _output_key = @Evaluate(1-@max(@Value(_input_red),@Value(_input_green),@Value(_input_blue)))
      SET_TO _output_cyan = @Evaluate((1-@Value(_input_red)-@Value(_output_key))/(1-@Value(_output_key)))
      SET_TO _output_magenta = @Evaluate((1-@Value(_input_green)-@Value(_output_key))/(1-@Value(_output_key)))
      SET_TO _output_yellow = @Evaluate((1-@Value(_input_blue)-@Value(_output_key))/(1-@Value(_output_key)))
    -> AttributeRounder
AttributeManager_11
    ATTR_TABLE:
      SET_TO _output_key = @Evaluate((1-@max(@Value(_input_red),@Value(_input_green),@Value(_input_blue)))*100)
      SET_TO _output_cyan = @Evaluate(((1-@Value(_input_red)-@Value(_output_key))/(1-@Value(_output_key)))*100)
      SET_TO _output_magenta = @Evaluate(((1-@Value(_input_green)-@Value(_output_key))/(1-@Value(_output_key)))*100)
      SET_TO _output_yellow = @Evaluate(((1-@Value(_input_blue)-@Value(_output_key))/(1-@Value(_output_key)))*100)
    -> AttributeRounder
AttributeRounder
    PLACES = 2
    ROUND_TYPE = Nearest
    SRC_ATTRS = _output_cyan _output_key _output_yellow _output_magenta
    -> AttributeManager_12
AttributeManager_12
    ATTR_TABLE = SET_TO _output_color = @Value(_output_cyan),@Value(_output_magenta),@Value(_output_yellow),@Value(_output_key)
    -> Output (output)
