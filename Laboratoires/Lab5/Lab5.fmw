FME workspace Lab5.fmw

Parameters:
- SourceDataset_CSV2 =
- SourceDataset_CSV2_3 =

Readers:
- CSV2_1: CSV2 from $(SourceDataset_CSV2)
- CSV2_2: CSV2 from $(SourceDataset_CSV2_3)
- ARCGISONLINEFEATURES_1: ARCGISONLINEFEATURES

Writers:
- ARCGISONLINEFEATURES_3: ARCGISONLINEFEATURES to <Unused>
- ARCGISONLINEFEATURES_2: ARCGISONLINEFEATURES to <Unused>

Note: https://sitewebbixi.s3.amazonaws.com/uploads/docs/20220107-donnees-ouvertes-8aa623.zip
CSV (reader CSV2_1)
    attributes: start_date varchar(24), emplacement_pk_start uint32, end_date varchar(24), emplacement_pk_end uint32, duration_sec uint32, is_member uint32, latitude y_coordinate, longitude x_coordinate, name varchar(68), pk uint32
    -> AttributeFilter
Note: https://sitewebbixi.s3.amazonaws.com/uploads/docs/20220108-donnees-ouvertes-816bd4.zip
CSV (reader CSV2_2) [off]
    attributes: start_date varchar(24), emplacement_pk_start uint32, end_date varchar(24), emplacement_pk_end uint32, duration_sec uint32, is_member uint32, latitude y_coordinate, longitude x_coordinate, name varchar(68), pk uint32
    -> AttributeFilter
CSV (writer ARCGISONLINEFEATURES_2)
    attributes: name String(68), pk Integer, start_total_count Integer, end_total_count Integer

Bookmark: New Bookmark
Creator [off]
    GEOMTYPE = Geometry Object
    NUM = 1
    CREATED -> HTTPCaller [off]
HTTPCaller [off]
    CONNECTION_TIMEOUT_LENGTH = 60
    ERROR_ATTR = _error
    FILE_PATH_ATTR2 = _response_file_path
    FILE_TYPE = .zip
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    OUTPUT_DIRNAME = /home/geo7630/geo7630/Laboratoires/Lab5
    REDIRECT_AUTH = ORIGINAL_DOMAIN_ONLY
    RESPONSE_TYPE = Folder
    SPLIT_MULTIPART_DOWNLOADS = NO
    STATUS_CODE_ATTR = _http_status_code
    TARGET_URL = https://sitewebbixi.s3.amazonaws.com/uploads/docs/20220107-donnees-ouvertes-8aa623.zip
    TRANSFER_TIMEOUT_LENGTH = 90
    USE_COOKIES = No
    VERIFY_SSL_CERTIFICATES = Yes
    -> ZipExtractor [off]
ZipExtractor [off]
    PRESERVE = No
    RECURSIVE = No
    REPLACE = No
    ROOT_FOLDER = /home/geo7630/geo7630/Laboratoires/Lab5
    ZIP_PATH = @Value(_response_file_path)
    File -> Tester [off]
    File -> Tester_2 [off]
Tester [off]
    BOOL_OP = OR
    COMPOSITE_TEST = 1
    TEST_CLAUSE = CASE_INSENSITIVE_TEST @Value(path_windows) CONTAINS stations
    TEST_MODE = TEST
    PASSED -> FeatureReader [INITIATOR] [off]
FeatureReader [off]
    ATTR_ACCUM_MODE = Only Use Result
    COMBINE_GEOM = Use Result
    CSV2_CASE_SENSITIVE_FIELD_NAMES = Yes
    CSV2_CHUNK_SIZE = 100000
    CSV2_DATA_START_LINE = 2
    CSV2_DATE_INPUT_FORMAT = FME
    CSV2_DELIMITER = auto
    CSV2_ENCODING = UTF-8
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = @Value(path_unix)
    FORMAT = CSV2
    INTERACT = NONE
    OUTPUT_FEATURES_DISPLAY = Schema and Data Features
Tester_2 [off]
    BOOL_OP = OR
    COMPOSITE_TEST = 1
    TEST_CLAUSE = CASE_INSENSITIVE_TEST @Value(path_windows) CONTAINS donnees_ouvertes
    TEST_MODE = CASE_INSENSITIVE_TEST

Bookmark: Juillet 2022
AttributeFilter
    ATTR_NAME = longitude
    ATTR_VALUES = <Empty>,<Missing>,<Null>,<Unfiltered>,-1
    <MISSING> -> StatisticsCalculator
    <MISSING> -> StatisticsCalculator_2
    <UNFILTERED> -> AttributeManager
StatisticsCalculator
    CALCULATION_MODE = NUMERIC
    FEAT_STATS = emplacement_pk_end,NUMERIC_MODE,,,COUNT,,,,,,,,,,
    GROUP_BY = emplacement_pk_end
    SUMMARY -> FeatureJoiner_2 [RIGHT]
StatisticsCalculator_2
    CALCULATION_MODE = NUMERIC
    FEAT_STATS = emplacement_pk_start,NUMERIC_MODE,,,COUNT,,,,,,,,,,
    GROUP_BY = emplacement_pk_start
    SUMMARY -> FeatureJoiner [RIGHT]
AttributeManager
    ATTR_TABLE:
      REMOVE start_date
      REMOVE emplacement_pk_start
      REMOVE end_date
      REMOVE emplacement_pk_end
      REMOVE duration_sec
      REMOVE is_member
      REMOVE latitude
      REMOVE longitude
    -> FeatureJoiner [LEFT]
FeatureJoiner
    ATTR_CONFLICT_RES = Use Left
    GEOMETRY_HANDLING = Use Left
    JOIN_KEYS = pk emplacement_pk_start AUTO
    JOIN_MODE = Full
    JOINED -> FeatureJoiner_2 [LEFT]
    <REJECTED> -> FeatureJoiner__Rejected_
FeatureJoiner_2
    ATTR_CONFLICT_RES = Use Left
    GEOMETRY_HANDLING = Use Left
    JOIN_KEYS = pk emplacement_pk_end AUTO
    JOIN_MODE = Full
    JOINED -> AttributeManager_2
    <REJECTED> -> FeatureJoiner_2__Rejected_
AttributeManager_2
    ATTR_TABLE:
      REMOVE emplacement_pk_start
      RENAME_SET_VALUE emplacement_pk_start.total_count > start_total_count
      REMOVE emplacement_pk_end
      RENAME_SET_VALUE emplacement_pk_end.total_count > end_total_count
    -> ChangeDetector [REVISED]
    -> CSV (writer ARCGISONLINEFEATURES_2)
FeatureJoiner_2__Rejected_: Logger
    LOG_FEATURE = LOG_ONLY
    MAXCOORDS = 20
    MAXFEATS = 20
    MESSAGE = Feature is:
    SEVERITY = INFO
FeatureJoiner__Rejected_: Logger
    LOG_FEATURE = LOG_ONLY
    MAXCOORDS = 20
    MAXFEATS = 20
    MESSAGE = Feature is:
    SEVERITY = INFO

Bookmark: New Bookmark
CSV (reader ARCGISONLINEFEATURES_1) [off]
    attributes: name String(68), pk Integer, start_total_count Integer, end_total_count Integer, OBJECTID OID
    -> ChangeDetector [ORIGINAL] [off]
    -> FeatureJoiner_3 [LEFT] [off]
ChangeDetector [off]
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCHATTRS = end_total_count name pk start_total_count
    MATCH_STRATEGY = Match Selected Attributes
    PREEMPTIVE_ATTRS = pk
    UNCHANGED_OUTPUT = Output Both
    UPDATED -> FeatureJoiner_3 [RIGHT] [off]
FeatureJoiner_3 [off]
    ATTR_CONFLICT_RES = Use Left
    GEOMETRY_HANDLING = Use Left
    JOIN_KEYS = pk pk AUTO
    JOIN_MODE = Inner
    JOINED -> AttributeManager_3 [off]
    <REJECTED> -> FeatureJoiner_3__Rejected_ [off]
AttributeManager_3 [off]
    ATTR_TABLE = REMOVE fme_db_operation
    -> CSV (writer ARCGISONLINEFEATURES_3) [off]
CSV (writer ARCGISONLINEFEATURES_3) [off]
    attributes: name String(68), pk Integer, start_total_count Integer, end_total_count Integer
FeatureJoiner_3__Rejected_: Logger [off]
    LOG_FEATURE = LOG_ONLY
    MAXCOORDS = 20
    MAXFEATS = 20
    MESSAGE = Feature is:
    SEVERITY = INFO

FME custom transformer ZipExtractor
Extracts files archived in a zip file, and then outputs features for every extracted file and directory.
    Each resulting feature has two attributes storing full path string of an extracted file/directory - 
    "path_unix"
    (UNIX style) and 
    "path_windows"
    (Windows style), and also has an attribute that indicates the depth of the file/directory in the extracted directory hierarchy - 
    "path_depth" 
    (integer starting from 1).
    The features containing file path will be output through the File port, and the features containing directory path will be output through the Directory port. 
    All the extracted files will be saved into a subfolder under the folder specified with the "Destination Root Folder" parameter. The subfolder name will be the same as the source zip file name without extension. For example, if the source zip file name is 
    "data.zip"
    and the specified root folder path is 
    "C:\root"
    , extracted files will be saved into 
    "C:\root\data"
    .
    If the same name folder exists under the specified root folder, a number will be added to the destination subfolder name as suffix to differentiate from the existing folder, by default. e.g. 
    "C:\root\data_1"
    , 
    "C:\root\data_2"
    , and so on. 
    If you set "Yes" to the "Replace Existing Destination Subfolder" parameter, the existing subfolder and all files within it will be removed, and then the destination subfolder will be created newly.
    By default, this transformer will NOT unzip zip files that are archived (nested) in the source zip file. If you set "Yes" to the "Unzip Nested Zip Files Recursively" parameter, this transformer unzips all the nested zip files recursively.
    All attributes of the input feature will be propagated to the output features, but the geometry and coordinate system will not be preserved.
    If the specified source zip file or destination root folder is invalid, the input feature will be output through the <Rejected> port.
    Note: The Unzipper (FME Hub) can also be used to unzip a zip file. The ZipExtractor may be useful if you need to specify the destination root folder and/or to unzip nested zip file(s).
Parameters
    Source Zip File
    :
    Specify a zip file that should be extracted. The zip file name has to end with the extension ".zip" (case insensitive) by default, but optionally, you can also specify any extension(s) which this transformer should attempt to extract as a zip file. See the Allowable Source/Nested Zip File Extensions parameter.
    Destination Root Folder
    :
    Specify a folder in which a subfolder containing all extracted files should be created. If you leave this parameter blank, this transformer treats the folder containing the source zip file as the destination root folder.
    All the extracted files will be saved into a subfolder under the root folder. The subfolder name will be the same as the source zip file name without extension. For example, if the source zip file name is 
    "data.zip"
    and the specified root folder path is 
    "C:\root"
    , extracted files will be saved into 
    "C:\root\data"
    .
    Replace Existing Destination Subfolder
    :
    By default, a number will be added to the destination subfolder name as suffix if the same name folder exists under the spcified root folder. e.g. 
    "C:\root\data_1"
    , 
    "C:\root\data_2"
    , and so on. If you set "Yes" to this parameter, the existing subfolder and all files within it will be removed, and then the destination subfolder will be created newly. 
    Unzip Nested Zip Files Recursively
    :
    By default, this transformer will NOT unzip zip files that are archived (nested) in the source zip file. If you set "Yes" to this parameter, this transformer unzips all the nested zip files recursively.
    Preserve Nested Zip Files
    :
    By default, zip files nested in the source zip file will be removed after unzipping them, when the "Unzip Nested Zip Files Recursively" parameter is set to "Yes". If you set "Yes" to this parameter, the nested zip files will also be preserved.
    This parameter affects the result only when the "Unzip Nested Zip Files Recursively" parameter is set to "Yes". When the "Unzip Nested Zip Files Recursively" is set to "No", nested zip files always will be preserved regardless of this parameter.
    Allowable Source/Nested Zip File Extension(s)
    :
    By default, this transformer accepts only zip files whose name end with the extension ".zip" (case insensitive). However, if you want to extract zip files with other extension, you can specify allowable extention(s) via these parameters, with space-separated format when specifying two or more.
    Here, "Source Zip File" means that the top level zip file which would be set to the Source Zip File parameter; "Nested Zip File"means that internal zip file(s) which have been archived within the source zip file.
    If you leave the parameter field blank (it's the default), only ".zip" (case insensitive) will be allowable as zip file extension.
    Note that "zip" won't be allowable if you have set one or more extension other than ".zip" to the parameter. If you want to allow ".zip" and other extension(s) simultaneously, specify all possible extensions including ".zip" with the parameter.
    The leading dot "." of extensions can be omitted.

Parameters:
- EXT_N =
- EXT_S =
- PRESERVE =
- RECURSIVE =
- REPLACE =
- ROOT_FOLDER =
- ZIP_PATH =

Input (input)
    -> ParameterFetcher
ParameterFetcher
    ATTR_LIST = __unzipper.zip_path {$(ZIP_PATH)} __unzipper.root_folder {$(ROOT_FOLDER)} __unzipper.replace {$(REPLACE)} __unzipper.recursive {$(RECURSIVE)} __unzipper.preserve {$(PRESERVE)} __unzipper.ext_s {$(EXT_S)} __unzipper.ext_n {$(EXT_N)}
    -> PythonCaller
PythonCaller
    HIDE_ATTRIBUTES = __unzipper.ext_n __unzipper.zip_path __unzipper.ext_s __unzipper.replace __unzipper.recursive __unzipper.root_folder __unzipper.preserve
    NEW_ATTRIBUTES = path_unix path_windows path_depth __unzipper.flag _error_message
    PYTHONSOURCE:
      # 2016-01-21, Takashi Iijima, Original Implementation
      # 2016-01-23, Takashi Iijima, Updated:
      # - added function to check file extension to prevent extracting non-archiver zip files. e.g. Excel (*.xlsx) etc.
      # - added codes to create desitnation root folder if it is specified but doesn't exist.
      # - added option to preserve nested zip files after unzipping them.
      # - added "path_depth" attribute to output features.
      # 2016-01-25, Takashi Iijima, Updated to trim leading and trailing whitespaces of specified path strings.
      # 2018-06-14, Takashi Iijima, Added Allowable Source/Nested Zip File Extention(s) parameter.
      # 2019-01-13, Takashi Iijima, Fixed the destination folder name derived from zip filename which has non-4-letters suffix (e.g. ".xlsx").
      # 2020-01-13, Takashi Iijima, Changed Default Python Interpreter to 3.6+, saved with FME 2017.1.2.1

      import fmeobjects, zipfile, os

      class ZipExtractor(object):
          def __init__(self):
              self.logger = fmeobjects.FMELogFile()
              self.kFlagFile = 'file'
              self.kFlagDirectory = 'directory'
              self.kFlagReject = 'reject'
              self.kFlagTerminate = 'terminate'
              self.zipExtS = set(['.zip']) # Filename extensions source (root) zip files
              self.zipExtN = set(['.zip']) # Filename extensions for archived (descendant) zip files

          # Returns the number of characters of the zip file extension
          # if the path points a valid zip file, 0 otherwise.
          def zipExtLen(self, path, zipExt):
              _, ext = os.path.splitext(path)
              return len(ext) if (ext.lower() in zipExt and zipfile.is_zipfile(path)) else 0

          def input(self, feature):
              # Retrieve parameter values from feature attributes, then remove the attributes.
              # Zip path may end with a path separator if extracted by the FilenamePartExtractor as "_dirpath".
              zipPath = feature.getAttribute('__unzipper.zip_path').strip().rstrip('\\/')
              rootFolder = feature.getAttribute('__unzipper.root_folder').strip()
              replace = (feature.getAttribute('__unzipper.replace') == 'Yes')
              self.recursive = (feature.getAttribute('__unzipper.recursive') == 'Yes')
              self.preserve = (feature.getAttribute('__unzipper.preserve') == 'Yes')
              extS = set(feature.getAttribute('__unzipper.ext_s').split())
              extN = set(feature.getAttribute('__unzipper.ext_n').split())
              feature.removeAttrsWithPrefix('__unzipper.')

              if extS:
                  self.zipExtS = set([(e if e.startswith('.') else ('.%s' % e)).lower() for e in extS])
              if extN:
                  self.zipExtN = set([(e if e.startswith('.') else ('.%s' % e)).lower() for e in extN])

              # If destination root folder is specified but doesn't exist, try creating the directory.
              isRootValid = True
              if rootFolder and not os.path.exists(rootFolder):
                  try:
                      os.makedirs(rootFolder)
                  except:
                      isRootValid = False

              # If specified zip file or destination root folder is invalid, reject the input feature.
              if not os.path.exists(zipPath) \
                  or self.zipExtLen(zipPath, self.zipExtS) == 0 \
                  or not isRootValid:
                  msg = 'Specified zip file or destination root folder is invalid.'
                  self.logger.logMessageString(msg, fmeobjects.FME_ERROR)
                  feature.setAttribute('_error_message', msg)
                  feature.setAttribute('__unzipper.flag', self.kFlagReject)
                  self.pyoutput(feature)
                  return

              # Define destination folder path: <root folder>/<source zip file name without extension>
              # If root folder is not specified, treat the folder containing source zip file as root folder.
              zipPath = os.path.abspath(zipPath)
              zipFolder, zipName = os.path.split(zipPath)
              rootName, _ = os.path.splitext(zipName)
              destFolder = os.path.join(os.path.abspath(rootFolder) if rootFolder else zipFolder, rootName)

              try:
                  # If the destination folder exists,
                  # - remove the existing folder and all files within it when REPLACE is set to Yes,
                  # - add suffix to the folder path when REPLACE is set to No.
                  if os.path.exists(destFolder):
                      if replace:
                          for dirpath, dirs, files in os.walk(destFolder, topdown=False):
                              for name in files:
                                  os.remove(os.path.join(dirpath, name))
                              for name in dirs:
                                  os.rmdir(os.path.join(dirpath, name))
                          os.rmdir(destFolder)
                      else:
                          format, n = '%s_%d', 1
                          while os.path.exists(format % (destFolder, n)): n += 1
                          destFolder = format % (destFolder, n)

                  # Extract the zip file and output features containing extracted file/directory path.
                  self.pathInfos = [] # tuples list - (file or directory path, flag: 'file' or 'directory', depth)
                  self.extract(zipPath, destFolder, 1)
                  for path, flag, depth in self.pathInfos:
                      feat = feature.cloneAttributes()
                      feat.setAttribute('path_unix', path.replace('\\', '/'))
                      feat.setAttribute('path_windows', path.replace('/', '\\'))
                      feat.setAttribute('path_depth', depth)
                      feat.setAttribute('__unzipper.flag', flag)
                      self.pyoutput(feat)

              except Exception as ex:
                  msg = 'Unexpected error: %s' % ex
                  self.logger.logMessageString(msg, fmeobjects.FME_ERROR)
                  feature.setAttribute('_error_message', msg)
                  feature.setAttribute('__unzipper.flag', self.kFlagTerminate)
                  self.pyoutput(feature)

          # Extract a zip file.
          def extract(self, zipPath, destPath, depth):
              with zipfile.ZipFile(zipPath) as z: z.extractall(destPath)
              self.findFiles(destPath, depth)

          # Find and collect extracted file/directory paths.
          def findFiles(self, dirPath, depth):
              self.pathInfos.append((dirPath, self.kFlagDirectory, depth))
              depth += 1
              for fname in os.listdir(dirPath):
                  path = os.path.join(dirPath, fname)
                  if os.path.isdir(path):
                      self.findFiles(path, depth)
                  elif self.recursive:
                      n = self.zipExtLen(path, self.zipExtN)
                      if n != 0:
                          if self.preserve:
                              self.pathInfos.append((path, self.kFlagFile, depth))
                              self.extract(path, os.path.join(dirPath, fname[:-n]), depth)
                          else:
                              self.extract(path, os.path.join(dirPath, fname[:-n]), depth)
                              os.remove(path)
                      else:
                          self.pathInfos.append((path, self.kFlagFile, depth))
                  else:
                      self.pathInfos.append((path, self.kFlagFile, depth))
    PYTHONSYMBOL = ZipExtractor
    -> AttributeFilter
AttributeFilter
    ATTR_NAME = __unzipper.flag
    ATTR_VALUES = file,directory,reject,terminate,<EMPTY>,<MISSING>,<NULL>,<UNFILTERED>
    file -> File (output)
    directory -> Directory (output)
    reject -> <Rejected> (output)
    terminate -> <Rejected> (output)
File (output)
Directory (output)
<Rejected> (output)
