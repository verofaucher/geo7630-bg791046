FME workspace Lab1.fmw

Parameters:
- DestDataset_POSTGIS =
- DestDataset_POSTGIS_3 =
- SourceDataset_CSV2 =
- SourceDataset_GEOJSON =

Readers:
- CSV2_1: CSV2 from $(SourceDataset_CSV2) in EPSG:4326
- GEOJSON_1: GEOJSON from $(SourceDataset_GEOJSON)

Writers:
- POSTGIS_1: POSTGIS to $(DestDataset_POSTGIS)
- POSTGIS_2: POSTGIS to $(DestDataset_POSTGIS_3)

parc_trees_h3_analysis (writer POSTGIS_1)
    attributes: tree_count int8, _h3index numeric(20,0)
parc_tree_density_analysis (writer POSTGIS_2)
    attributes: parc_name text, parc_code text, parc_area_m2 text, parc_type_1 text, parc_type_2 text, tree_count int8, tree_density float8, tree_count_median float8, tree_density_median float8, parc_tree_density_index float8

Bookmark: Lire les données d'arbres depuis les données ouvertes CSV
CSV (reader CSV2_1)
    attributes: INV_TYPE varchar(2), EMP_NO real64, ARROND uint32, ARROND_NOM varchar(24), Rue varchar(1), COTE varchar(1), No_civique varchar(1), Emplacement varchar(24), Coord_X time, Coord_Y real64, SIGLE varchar(7), Essence_latin varchar(46), Essence_fr varchar(49), ESSENCE_ANG varchar(45), DHP real32, Date_releve varchar(20), Date_plantation varchar(20), LOCALISATION varchar(1), CODE_PARC varchar(9), NOM_PARC varchar(43), Longitude x_coordinate, Latitude y_coordinate
    -> Reprojector
Note: Reprojection 4326 - 3857
Reprojector
    DEST = EPSG:3857
    INTERPOLATION_TYPE_NAME = Nearest Neighbor
    RASTER_CELL_SIZE = Preserve Cells
    RASTER_TOLERANCE = 0.0
    SOURCE = EPSG:4326
    REPROJECTED -> GeometryExtractor

Bookmark: Facultatif mais bonne pratique
GeometryExtractor
    ATTR = _geometry
    ELLIPSOID_NAME = WGS84
    GENERATE_GEOMETRY_IDS = No
    GEOHASH_PRECISION_DISPLAY = ~9.3 mm (12 characters)
    ISO6709_FORMAT_CHOICE = Degrees and Decimal Degrees
    ISO6709_MAX_DECIMAL_PLACES = 5
    JSON_MAX_DIGITS = 7
    KIND_LONG = FME Binary
    LETTERING = WGS84
    LEVELS_ATTR = _levels
    MSSQL_FORMAT_CHOICE = Geometry
    OGCVERSION = 1.2
    OGC_WKT_PRECISION_DISPLAY = 64-bit
    OGEOSMS_URL_PREFIX = http://maps.google.com/?q=
    OMIT_NAMESPACES_DISPLAY = No
    PRECISION = 0
    PREFER_POLYGON_OVER_SURFACE = No
    REMOVE_GEOMETRY = No
    -> GeometryValidator
GeometryValidator
    ISSUE_ATTR_NAME = _issues
    PRESETS = Basic Integrity
    REPAIR = Yes
    RULES = NAN_REMOVAL PROCESS_MEASURE]NO]FME_CONTROLLER_QUERY_FILE]transformers/dependencies/geometryvalidator8/NAN_REMOVAL.fme NULL_REMOVAL FME_CONTROLLER_QUERY_FILE]transformers/dependencies/geometryvalidator8/NULL_REMOVAL.fme]FME_CONTROLLER_CHOICE]NULL_REMOVAL TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme
    SUMMARY = Detailed
    PASSED -> PointOnAreaOverlayer [POINT]
    PASSED -> PointOnAreaOverlayer_2 [POINT]

Bookmark: Lire les données de parc depuis le site des données ouvertes GEOJSON
Note: Lire le geojson des parcs depuis le site des données ouvertes
espvert.esv_espace_vert_vue_datefin_null (reader GEOJSON_1)
    attributes: OBJECTID string, Type string, Lien string, Nom string, NUM_INDEX string, SUPERFICIE string, PROPRIETE string, GESTION string, COMPETENCE string, TYPO1 string, TYPO2 string
    -> Reprojector_2
    -> H3HexagonalIndexer_2
Note: Reprojection 4326 vers 3857
Reprojector_2
    DEST = EPSG:3857
    INTERPOLATION_TYPE_NAME = Nearest Neighbor
    RASTER_CELL_SIZE = Preserve Cells
    RASTER_TOLERANCE = 0.0
    REPROJECTED -> GeometryExtractor_2

Bookmark: Création des tuiles hexagonales h3 pour chaque parc
H3HexagonalIndexer_2
    INDEX_OPERATION = Filling Indexes
    -> Reprojector_3
    <REJECTED> -> H3HexagonalIndexer_2__Rejected_
Reprojector_3
    DEST = EPSG:3857
    INTERPOLATION_TYPE_NAME = Nearest Neighbor
    RASTER_CELL_SIZE = Preserve Cells
    RASTER_TOLERANCE = 0.0
    REPROJECTED -> PointOnAreaOverlayer_2 [AREA]
H3HexagonalIndexer_2__Rejected_: Logger
    LOG_FEATURE = LOG_ONLY
    MAXCOORDS = 20
    MAXFEATS = 20
    MESSAGE = Feature is:
    SEVERITY = INFO

Bookmark: Intersection spatiale entre les tuiles hexagonales et les arbres pour calculer la densité
Note: Intersection spatiale
PointOnAreaOverlayer_2
    ATTR_ACCUM_MODE = Merge Incoming
    ATTR_CONFLICT_RES = Use Original
    DEAGGREGATE_INPUT = Yes
    OV_ATTR = point_count
    POLYS_FIRST = NO
    AREA -> AttributeKeeper_2
    <REJECTED> -> PointOnAreaOverlayer_2__Rejected_
Note: On garde seulement les champs voulus
AttributeKeeper_2
    CREATE_BULK_MODE_FEATURES = NO
    KEEP_ATTRS = point_count,_geometry,_h3index
    -> AttributeManager_3
AttributeManager_3
    ATTR_TABLE:
      RENAME_SET_VALUE point_count > tree_count
      REMOVE _geometry
    -> parc_trees_h3_analysis (writer POSTGIS_1)
PointOnAreaOverlayer_2__Rejected_: Logger
    LOG_FEATURE = LOG_ONLY
    MAXCOORDS = 20
    MAXFEATS = 20
    MESSAGE = Feature is:
    SEVERITY = INFO

Bookmark: Facultatif mais bonnes pratiques
GeometryExtractor_2
    ATTR = _geometry
    ELLIPSOID_NAME = WGS84
    GENERATE_GEOMETRY_IDS = No
    GEOHASH_PRECISION_DISPLAY = ~9.3 mm (12 characters)
    ISO6709_FORMAT_CHOICE = Degrees and Decimal Degrees
    ISO6709_MAX_DECIMAL_PLACES = 5
    JSON_MAX_DIGITS = 7
    KIND_LONG = FME Binary
    LETTERING = WGS84
    LEVELS_ATTR = _levels
    MSSQL_FORMAT_CHOICE = Geometry
    OGCVERSION = 1.2
    OGC_WKT_PRECISION_DISPLAY = 64-bit
    OGEOSMS_URL_PREFIX = http://maps.google.com/?q=
    OMIT_NAMESPACES_DISPLAY = No
    PRECISION = 0
    PREFER_POLYGON_OVER_SURFACE = No
    REMOVE_GEOMETRY = No
    -> GeometryValidator_2
GeometryValidator_2
    ISSUE_ATTR_NAME = _issues
    PRESETS = Basic Integrity
    REPAIR = Yes
    RULES = NAN_REMOVAL PROCESS_MEASURE]NO]FME_CONTROLLER_QUERY_FILE]transformers/dependencies/geometryvalidator8/NAN_REMOVAL.fme NULL_REMOVAL FME_CONTROLLER_QUERY_FILE]transformers/dependencies/geometryvalidator8/NULL_REMOVAL.fme]FME_CONTROLLER_CHOICE]NULL_REMOVAL TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme
    SUMMARY = Detailed
    PASSED -> PointOnAreaOverlayer [AREA]

Bookmark: Intersection spatiale Arbres VS Parcs
PointOnAreaOverlayer
    ATTR_ACCUM_MODE = Merge Incoming
    ATTR_CONFLICT_RES = Use Original
    DEAGGREGATE_INPUT = Yes
    OV_ATTR = point_count
    POLYS_FIRST = NO
    AREA -> AttributeKeeper
    <REJECTED> -> PointOnAreaOverlayer__Rejected_
Note: On choisit seulement les attributs nécessaires
AttributeKeeper
    CREATE_BULK_MODE_FEATURES = NO
    KEEP_ATTRS = Nom,point_count,SUPERFICIE,TYPO1,TYPO2,_geometry,NUM_INDEX
    -> AttributeCreator
Note: Calcul densité d'arbres par m2 par parc
AttributeCreator
    ATTR_TABLE = SET_TO densite = @Evaluate(@Value(point_count)/@Value(SUPERFICIE))
    -> AttributeManager
Note: Renomme les champs
AttributeManager
    ATTR_TABLE:
      RENAME_SET_VALUE Nom > parc_name
      RENAME_SET_VALUE NUM_INDEX > parc_code
      RENAME_SET_VALUE SUPERFICIE > parc_area_m2
      RENAME_SET_VALUE TYPO1 > parc_type_1
      RENAME_SET_VALUE TYPO2 > parc_type_2
      RENAME_SET_VALUE point_count > tree_count
      RENAME_SET_VALUE densite > tree_density
      RENAME_SET_VALUE _geometry > geom
    -> StatisticsCalculator
Note: Calcul de la mediane de densité
StatisticsCalculator
    CALCULATION_MODE = NUMERIC
    FEAT_STATS = tree_count,NUMERIC_MODE,,,,,,MEDIAN,,,,,,,;tree_density,NUMERIC_MODE,,,,,,MEDIAN,,,,,,,
    COMPLETE -> AttributeManager_2
Note: Calcul de l'index de densité
AttributeManager_2
    ATTR_TABLE = SET_TO parc_tree_density_index = @Evaluate((@Value(tree_density)/@Value(tree_density.median))*100)
    USER_EXPOSED_ATTRIBUTES = parc_tree_density_index
    -> NullAttributeMapper
Note: On attache un logger pour prévenir des erreurs et ne pas arrêter le flux de traitement
PointOnAreaOverlayer__Rejected_: Logger
    LOG_FEATURE = LOG_ONLY
    MAXCOORDS = 20
    MAXFEATS = 20
    MESSAGE = Feature is:
    SEVERITY = INFO

Bookmark: Nettoyage des vides, et null et valeurs manquantes
NullAttributeMapper
    ATTRCHOICE = All Attributes
    NULL_TREATMENT = Null
    OTHER_VALUE = :
    REG_EXP = " "
    SOURCE_ATTR_VAL = Null
    -> parc_tree_density_analysis (writer POSTGIS_2)
