FME workspace bg791046.fmw

Parameters:
- DestDataset_POSTGIS =
- SourceDataset_GEOJSON =
- SourceDataset_GEOJSON_3 =

Readers:
- GEOJSON_1: GEOJSON from $(SourceDataset_GEOJSON)
- GEOJSON_2: GEOJSON from $(SourceDataset_GEOJSON_3)

Writers:
- POSTGIS_1: POSTGIS to $(DestDataset_POSTGIS)

OCcupation commerciale 2022 (reader GEOJSON_1)
    attributes: ID string, ORIGINE string, T_COMMERCE string, DATE_RECENSEMENT string, CIVIQUE string, TYPE_VOIE string, LIEN_VOIE string, NOM_VOIE string, ORIENTATION string, ADRESSE string, SUITE string, CODE_POST string, ETAGE string, NOM_CENTRE string, NOM_ETAB string, ID_USAGE1 string, USAGE1 string, ID_USAGE2 string, USAGE2 string, ID_USAGE3 string, USAGE3 string, SCIAN string, SITEWEB string, SITE_TRANSACTIONNEL string, ACCES_MOBILITE_REDUITE string, VACANT_A_LOUER string, A_LOUER_CONTACT string, A_LOUER_TELEPHONE string, ARRONDISSEMENT string, QUARTIER string,
      SDC_NOM string, SECTEUR_PME string, ENFANT string, MULTIUSAGE string, MULTIOCCUPANT string, NEQ string, SUFFIXE_NEQ string, COORDX string, COORDY string, LAT string, LONG string
    -> Reprojector
Reprojector
    DEST = EPSG:3857
    INTERPOLATION_TYPE_NAME = Nearest Neighbor
    RASTER_CELL_SIZE = Preserve Cells
    RASTER_TOLERANCE = 0.0
    REPROJECTED -> VertexCreator
VertexCreator
    MEASURE_TYPE = Continuous
    MODE_NAME = Replace with Point
    XVAL = @Value(LONG)
    YVAL = @Value(LAT)
    -> AttributeFilter
AttributeFilter
    ATTR_NAME = NOM_ETAB
    ATTR_VALUES = <Empty>,<Missing>,<Null>,<Unfiltered>,VACANT
    VACANT -> PointOnAreaOverlayer [POINT]
limites-terrestres (reader GEOJSON_2)
    attributes: DefaultAtt string
    -> H3HexagonalIndexer
H3HexagonalIndexer
    INDEX_OPERATION = Filling Indexes
    <REJECTED> -> Logger
Logger
    LOG_FEATURE = LOG_ONLY
    MAXCOORDS = 20
    MAXFEATS = 20
    MESSAGE = Feature is:
    SEVERITY = INFO
    LOGGED -> Dissolver
Dissolver
    ACCUM_INPUT_ATTRS = Use Attributes From One Feature
    CLEANING_TOLERANCE = Automatic
    CONNECT_Z_MODE = First Wins
    DEAGGREGATE_INPUT = Yes
    AREA -> Reprojector_2
Reprojector_2
    DEST = EPSG:3857
    INTERPOLATION_TYPE_NAME = Nearest Neighbor
    RASTER_CELL_SIZE = Preserve Cells
    RASTER_TOLERANCE = 0.0
    REPROJECTED -> PointOnAreaOverlayer [AREA]
PointOnAreaOverlayer
    ATTR_ACCUM_MODE = Merge Incoming
    ATTR_CONFLICT_RES = Use Original
    CANDIDATE_LIST_ATTRS_TO_INCLUDE_MODE = Selected Attributes
    DEAGGREGATE_INPUT = Yes
    OV_ATTR = _overlaps
    POLYS_FIRST = No
    POINT -> bg791046 (writer POSTGIS_1)
    AREA -> bg791046 (writer POSTGIS_1)
bg791046 (writer POSTGIS_1)
    attributes: defaultatt text, fme_rejection_code text, fme_rejection_message text, _overlaps int8, id text, origine text, t_commerce text, date_recensement text, civique text, type_voie text, lien_voie text, nom_voie text, orientation text, adresse text, suite text, code_post text, etage text, nom_centre text, nom_etab text, id_usage1 text, usage1 text, id_usage2 text, usage2 text, id_usage3 text, usage3 text, scian text, siteweb text, site_transactionnel text, acces_mobilite_reduite text, vacant_a_louer text,
      a_louer_contact text, a_louer_telephone text, arrondissement text, quartier text, sdc_nom text, secteur_pme text, enfant text, multiusage text, multioccupant text, neq text, suffixe_neq text, coordx text, coordy text, lat text, long text
