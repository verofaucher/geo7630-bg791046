FME workspace tp2.fmw

Parameters:
- DestDataset_MBTILES = /home/geo7630/geo7630/Laboratoires/Laboratoire 2   # Destination MBTiles Folder
- SourceDataset_CSV2 = https://data.montreal.ca/dataset/63ca34cd-d636-420c-929b-cac47116f2e5/resource/d99f8ff2-55ae-4581-920e-146219c5f429/download/arbres-abattages.csv   # Source CSV (Comma Separated Value) File(s)
- SourceDataset_CSV2_5 = https://data.montreal.ca/dataset/ebb813dd-a93f-4fb0-8137-80492a30a1fa/resource/b68cb3fc-b6ab-4472-a831-4e1bbaf8346b/download/injectionfrenepublic2018.csv   # Source CSV (Comma Separated Value) File(s)
- SourceDataset_SHAPEFILE = fme://microsoft-onedrive/canopee-2007-ahuntsic-cartierville.shp?id=b%21VeExegk85E6cT0SkEe1_hrBjFFYGtG5Ph3pq-0u0sFSu7J4IAWdzRY3ldZAyl_hf%3A%3A01K4RD4M7TETG4UBZBERBI6656FIMVSXPD&module=microsoftonedrive&webservice=Microsoft%20OneDrive&connection=geo7630%20Microsoft%20OneDrive%20%28Graph%2900   # Source Esri Shapefile(s)
- SourceDataset_SHAPEFILE_33 = fme://microsoft-onedrive/canopee-2007-anjou.shp?id=b%21VeExegk85E6cT0SkEe1_hrBjFFYGtG5Ph3pq-0u0sFSu7J4IAWdzRY3ldZAyl_hf%3A%3A01K4RD4M4DEHFSVAP7KVFKIE3ZCJ3CYJZT&module=microsoftonedrive&webservice=Microsoft%20OneDrive&connection=geo7630%20Microsoft%20OneDrive%20%28Graph%2900   # Source Esri Shapefile(s)
- SourceDataset_SHAPEFILE_25 = fme://microsoft-onedrive/canopee-2007-cdn-ndg.shp?id=b%21VeExegk85E6cT0SkEe1_hrBjFFYGtG5Ph3pq-0u0sFSu7J4IAWdzRY3ldZAyl_hf%3A%3A01K4RD4MY6NDN5WLP7G5CIFAFZ4NZCG5WR&module=microsoftonedrive&webservice=Microsoft%20OneDrive&connection=geo7630%20Microsoft%20OneDrive%20%28Graph%2900   # Source Esri Shapefile(s)
- SourceDataset_SHAPEFILE_29 = fme://microsoft-onedrive/canopee-2007-lachine.shp?id=b%21VeExegk85E6cT0SkEe1_hrBjFFYGtG5Ph3pq-0u0sFSu7J4IAWdzRY3ldZAyl_hf%3A%3A01K4RD4M3MJR534YWEFBGJCJQLVEYGGMBA&module=microsoftonedrive&webservice=Microsoft%20OneDrive&connection=geo7630%20Microsoft%20OneDrive%20%28Graph%2900   # Source Esri Shapefile(s)
- SourceDataset_SHAPEFILE_37 = fme://microsoft-onedrive/canopee-2007-lasalle.shp?id=b%21VeExegk85E6cT0SkEe1_hrBjFFYGtG5Ph3pq-0u0sFSu7J4IAWdzRY3ldZAyl_hf%3A%3A01K4RD4M2VUUSQFUXD6NG2NONFUZFAE3XM&module=microsoftonedrive&webservice=Microsoft%20OneDrive&connection=geo7630%20Microsoft%20OneDrive%20%28Graph%2900   # Source Esri Shapefile(s)
- SourceDataset_SHAPEFILE_43 = fme://microsoft-onedrive/canopee-2007-le-plateau-mont-royal.shp?id=b%21VeExegk85E6cT0SkEe1_hrBjFFYGtG5Ph3pq-0u0sFSu7J4IAWdzRY3ldZAyl_hf%3A%3A01K4RD4M65JHMO2NUP7JH3JWL7CPDB74L6&module=microsoftonedrive&webservice=Microsoft%20OneDrive&connection=geo7630%20Microsoft%20OneDrive%20%28Graph%2900   # Source Esri Shapefile(s)
- SourceDataset_SHAPEFILE_27 = fme://microsoft-onedrive/canopee-2007-le-sud-ouest.shp?id=b%21VeExegk85E6cT0SkEe1_hrBjFFYGtG5Ph3pq-0u0sFSu7J4IAWdzRY3ldZAyl_hf%3A%3A01K4RD4M5Z4PXM7TUXZND3JHZCG7ZV5ZJX&module=microsoftonedrive&webservice=Microsoft%20OneDrive&connection=geo7630%20Microsoft%20OneDrive%20%28Graph%2900   # Source Esri Shapefile(s)
- SourceDataset_SHAPEFILE_31 = fme://microsoft-onedrive/canopee-2007-mercier-hochelaga-maisonneuve.shp?id=b%21VeExegk85E6cT0SkEe1_hrBjFFYGtG5Ph3pq-0u0sFSu7J4IAWdzRY3ldZAyl_hf%3A%3A01K4RD4M2PJEP2AFDSGFAZ65HEVFLEXHDB&module=microsoftonedrive&webservice=Microsoft%20OneDrive&connection=geo7630%20Microsoft%20OneDrive%20%28Graph%2900   # Source Esri Shapefile(s)
- SourceDataset_SHAPEFILE_35 = fme://microsoft-onedrive/canopee-2007-montreal-nord.shp?id=b%21VeExegk85E6cT0SkEe1_hrBjFFYGtG5Ph3pq-0u0sFSu7J4IAWdzRY3ldZAyl_hf%3A%3A01K4RD4M6GRPZFGDLKCVFLD2TJLP4UQRKN&module=microsoftonedrive&webservice=Microsoft%20OneDrive&connection=geo7630%20Microsoft%20OneDrive%20%28Graph%2900   # Source Esri Shapefile(s)
- SourceDataset_SHAPEFILE_39 = fme://microsoft-onedrive/canopee-2007-outremont.shp?id=b%21VeExegk85E6cT0SkEe1_hrBjFFYGtG5Ph3pq-0u0sFSu7J4IAWdzRY3ldZAyl_hf%3A%3A01K4RD4M35C4WLVF6YBBGJKQP4KYNZC7HR&module=microsoftonedrive&webservice=Microsoft%20OneDrive&connection=geo7630%20Microsoft%20OneDrive%20%28Graph%2900   # Source Esri Shapefile(s)
- SourceDataset_SHAPEFILE_41 = fme://microsoft-onedrive/canopee-2007-pierrefonds-roxboro.shp?id=b%21VeExegk85E6cT0SkEe1_hrBjFFYGtG5Ph3pq-0u0sFSu7J4IAWdzRY3ldZAyl_hf%3A%3A01K4RD4M7WDLY3Z5QS3JEJZ3EM26CGKL6C&module=microsoftonedrive&webservice=Microsoft%20OneDrive&connection=geo7630%20Microsoft%20OneDrive%20%28Graph%2900   # Source Esri Shapefile(s)
- SourceDataset_SHAPEFILE_24 = fme://microsoft-onedrive/canopee-2007-rdp-pat.shp?id=b%21VeExegk85E6cT0SkEe1_hrBjFFYGtG5Ph3pq-0u0sFSu7J4IAWdzRY3ldZAyl_hf%3A%3A01K4RD4M25BRQYMOL6EBEZLVIKRCRTWB6Y&module=microsoftonedrive&webservice=Microsoft%20OneDrive&connection=geo7630%20Microsoft%20OneDrive%20%28Graph%2900   # Source Esri Shapefile(s)
- SourceDataset_SHAPEFILE_26 = fme://microsoft-onedrive/canopee-2007-rosemont-la-petite-patrie.shp?id=b%21VeExegk85E6cT0SkEe1_hrBjFFYGtG5Ph3pq-0u0sFSu7J4IAWdzRY3ldZAyl_hf%3A%3A01K4RD4MYC5IUCLSBR4RFJJZT6IKUCRBCX&module=microsoftonedrive&webservice=Microsoft%20OneDrive&connection=geo7630%20Microsoft%20OneDrive%20%28Graph%2900   # Source Esri Shapefile(s)
- SourceDataset_SHAPEFILE_28 = fme://microsoft-onedrive/canopee-2007-saint-laurent.shp?id=b%21VeExegk85E6cT0SkEe1_hrBjFFYGtG5Ph3pq-0u0sFSu7J4IAWdzRY3ldZAyl_hf%3A%3A01K4RD4MYCTRSUEHUO5JBIYDOFVCZFKF2Q&module=microsoftonedrive&webservice=Microsoft%20OneDrive&connection=geo7630%20Microsoft%20OneDrive%20%28Graph%2900   # Source Esri Shapefile(s)
- SourceDataset_SHAPEFILE_30 = fme://microsoft-onedrive/canopee-2007-saint-leonard.shp?id=b%21VeExegk85E6cT0SkEe1_hrBjFFYGtG5Ph3pq-0u0sFSu7J4IAWdzRY3ldZAyl_hf%3A%3A01K4RD4M2Z6POJEJZY6FFJ2D3LCNQBRUEJ&module=microsoftonedrive&webservice=Microsoft%20OneDrive&connection=geo7630%20Microsoft%20OneDrive%20%28Graph%2900   # Source Esri Shapefile(s)
- SourceDataset_SHAPEFILE_32 = fme://microsoft-onedrive/canopee-2007-verdun.shp?id=b%21VeExegk85E6cT0SkEe1_hrBjFFYGtG5Ph3pq-0u0sFSu7J4IAWdzRY3ldZAyl_hf%3A%3A01K4RD4M5TYDOVYNEGDFFLR6YCRQRH5F6K&module=microsoftonedrive&webservice=Microsoft%20OneDrive&connection=geo7630%20Microsoft%20OneDrive%20%28Graph%2900   # Source Esri Shapefile(s)
- SourceDataset_SHAPEFILE_34 = fme://microsoft-onedrive/canopee-2007-ville-marie.shp?id=b%21VeExegk85E6cT0SkEe1_hrBjFFYGtG5Ph3pq-0u0sFSu7J4IAWdzRY3ldZAyl_hf%3A%3A01K4RD4M2WQNMKWMU6YFFZDKQZ2X524FJP&module=microsoftonedrive&webservice=Microsoft%20OneDrive&connection=geo7630%20Microsoft%20OneDrive%20%28Graph%2900   # Source Esri Shapefile(s)
- SourceDataset_SHAPEFILE_38 = fme://microsoft-onedrive/canopee-2019.shp?id=b%21VeExegk85E6cT0SkEe1_hrBjFFYGtG5Ph3pq-0u0sFSu7J4IAWdzRY3ldZAyl_hf%3A%3A01K4RD4MZCXTUN6QZ6UNCYBZPW5WJZ2QAS&module=microsoftonedrive&webservice=Microsoft%20OneDrive&connection=geo7630%20Microsoft%20OneDrive%20%28Graph%2900   # Source Esri Shapefile(s)
- SourceDataset_SHAPEFILE_36 = fme://microsoft-onedrive/canopee-2007-villeray-saint-michel-parc-extension.shp?id=b%21VeExegk85E6cT0SkEe1_hrBjFFYGtG5Ph3pq-0u0sFSu7J4IAWdzRY3ldZAyl_hf%3A%3A01K4RD4M5HWO2DPTJY2VC2S7PMS2UEMGQI&module=microsoftonedrive&webservice=Microsoft%20OneDrive&connection=geo7630%20Microsoft%20OneDrive%20%28Graph%2900   # Source Esri Shapefile(s)
- SourceDataset_SHAPEFILE_40 = fme://microsoft-onedrive/canopee-2015.shp?id=b%21VeExegk85E6cT0SkEe1_hrBjFFYGtG5Ph3pq-0u0sFSu7J4IAWdzRY3ldZAyl_hf%3A%3A01K4RD4MZRWCZFLQ4RHVHY2L6UOUNBTY7W&module=microsoftonedrive&webservice=Microsoft%20OneDrive&connection=geo7630%20Microsoft%20OneDrive%20%28Graph%29   # Source Esri Shapefile(s)
- SourceDataset_SHAPEFILE_23 = fme://microsoft-onedrive/canopee-2007-ile-bizard-sainte-genevieve.shp?id=b%21VeExegk85E6cT0SkEe1_hrBjFFYGtG5Ph3pq-0u0sFSu7J4IAWdzRY3ldZAyl_hf%3A%3A01K4RD4M26FBKVFFPHE5FY5TOYPUOCHDJ6&module=microsoftonedrive&webservice=Microsoft%20OneDrive&connection=geo7630%20Microsoft%20OneDrive%20%28Graph%2900   # Source Esri Shapefile(s)
- DestDataset_POSTGIS_17 = GEO7630   # Connection
- DestDataset_POSTGIS_13 = GEO7630   # Connection
- DestDataset_POSTGIS_11 = GEO7630   # Connection
- DestDataset_POSTGIS_15 = GEO7630   # Connection
- SourceDataset_GEOJSON = https://data.montreal.ca/dataset/9797a946-9da8-41ec-8815-f6b276dec7e9/resource/6b313375-d9bc-4dc3-af8e-ceae3762ae6e/download/limites-administratives-agglomeration-nad83.geojson   # Source GeoJSON File or URL
- DestDataset_POSTGIS_10 = GEO7630   # Connection
- SourceDataset_LAS = http://depot.ville.montreal.qc.ca/geomatique/lidar_aerien/2015/292-5045_2015.laz   # Source ASPRS LAS File(s)
- DestDataset_POSTGIS_16 = GEO7630   # Connection
- SourceDataset_CSV2_6 = https://data.montreal.ca/dataset/b89fd27d-4b49-461b-8e54-fa2b34a628c4/resource/64e28fe6-ef37-437a-972d-d1d3f1f7d891/download/arbres-publics.csv   # Source CSV (Comma Separated Value) File(s)
- SourceDataset_TIFF_3 = http://depot.ville.montreal.qc.ca/geomatique/photo_aerienne/2003/HM03033-279.tif   # Source TIFF (Tagged Image File Format) File(s)
- DestDataset_TIFF = /home/geo7630/Desktop/Travail   # Destination TIFF (Tagged Image File Format) Folder

Readers:
- CSV2_1: CSV2 from $(SourceDataset_CSV2)
- CSV2_2: CSV2 from $(SourceDataset_CSV2_5)
- SHAPEFILE_1: SHAPEFILE from $(SourceDataset_SHAPEFILE)
- SHAPEFILE_2: SHAPEFILE from $(SourceDataset_SHAPEFILE_33)
- SHAPEFILE_3: SHAPEFILE from $(SourceDataset_SHAPEFILE_25)
- SHAPEFILE_4: SHAPEFILE from $(SourceDataset_SHAPEFILE_23)
- SHAPEFILE_5: SHAPEFILE from $(SourceDataset_SHAPEFILE_29)
- SHAPEFILE_6: SHAPEFILE from $(SourceDataset_SHAPEFILE_37)
- SHAPEFILE_7: SHAPEFILE from $(SourceDataset_SHAPEFILE_43)
- SHAPEFILE_8: SHAPEFILE from $(SourceDataset_SHAPEFILE_27)
- SHAPEFILE_9: SHAPEFILE from $(SourceDataset_SHAPEFILE_31)
- SHAPEFILE_10: SHAPEFILE from $(SourceDataset_SHAPEFILE_35)
- SHAPEFILE_11: SHAPEFILE from $(SourceDataset_SHAPEFILE_39)
- SHAPEFILE_12: SHAPEFILE from $(SourceDataset_SHAPEFILE_41)
- SHAPEFILE_13: SHAPEFILE from $(SourceDataset_SHAPEFILE_24)
- SHAPEFILE_14: SHAPEFILE from $(SourceDataset_SHAPEFILE_26)
- SHAPEFILE_15: SHAPEFILE from $(SourceDataset_SHAPEFILE_28)
- SHAPEFILE_16: SHAPEFILE from $(SourceDataset_SHAPEFILE_30)
- SHAPEFILE_17: SHAPEFILE from $(SourceDataset_SHAPEFILE_32)
- SHAPEFILE_18: SHAPEFILE from $(SourceDataset_SHAPEFILE_34)
- SHAPEFILE_19: SHAPEFILE from $(SourceDataset_SHAPEFILE_38)
- SHAPEFILE_20: SHAPEFILE from $(SourceDataset_SHAPEFILE_36)
- SHAPEFILE_21: SHAPEFILE from $(SourceDataset_SHAPEFILE_40)
- GEOJSON_1: GEOJSON from $(SourceDataset_GEOJSON)
- LAS_1: LAS from $(SourceDataset_LAS)
- CSV2_4: CSV2 from $(SourceDataset_CSV2_6)
- TIFF_2: TIFF from $(SourceDataset_TIFF_3)

Writers:
- POSTGIS_2: POSTGIS to $(DestDataset_POSTGIS_17)
- POSTGIS_3: POSTGIS to $(DestDataset_POSTGIS_13)
- POSTGIS_4: POSTGIS to $(DestDataset_POSTGIS_11)
- POSTGIS_5: POSTGIS to $(DestDataset_POSTGIS_15)
- POSTGIS_6: POSTGIS to $(DestDataset_POSTGIS_10)
- POSTGIS_9: POSTGIS to $(DestDataset_POSTGIS_16)
- MBTILES_1: MBTILES to $(DestDataset_MBTILES)
- TIFF_1: TIFF to $(DestDataset_TIFF)

Bookmark: Arbres abbatus
Note: Données des arbres abbatus sous forme de table
CSV (reader CSV2_1)
    attributes: ARH_TYPE varchar(2), ARH_EMP_NO uint32, ARH_NO uint32, ARH_ESSENCE varchar(7), ARH_DATE_ABATTAGE varchar(20), Coord_X x_coordinate, Coord_Y y_coordinate, Longitude real64, Latitude real64
    -> Reprojector
Note: Reprojection de EPSG:2950 vers EPSG:3857
Reprojector
    DEST = EPSG:3857
    INTERPOLATION_TYPE_NAME = Nearest Neighbor
    RASTER_CELL_SIZE = Preserve Cells
    RASTER_TOLERANCE = 0.0
    SOURCE = EPSG:4326
    REPROJECTED -> GeometryExtractor
Note: Conversion des données en couches vectorielles
GeometryExtractor
    ATTR = _geometry
    KIND_LONG = FME Binary
    REMOVE_GEOMETRY = No
    -> GeometryValidator
Note: Valider si les données sont praticables
GeometryValidator
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme CONSECUTIVE_IDENTICAL_VERTICES_2D CHECK_Z]YES]FME_CONTROLLER_QUERY_FILE]transformers/dependencies/geometryvalidator8/CONSECUTIVE_IDENTICAL_VERTICES_2D.fme MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme NULL_REMOVAL FME_CONTROLLER_QUERY_FILE]transformers/dependencies/geometryvalidator8/NULL_REMOVAL.fme]FME_CONTROLLER_CHOICE]NULL_REMOVAL OGC_SIMPLE_CHECK LEGACY_OGC]No]FME_CONTROLLER_QUERY_FILE]transformers/dependencies/geometryvalidator8/OGC_SIMPLE_CHECK.fme OGC_VALID_CHECK OGC_VERSION]V1.2.0]FME_CONTROLLER_QUERY_FILE]transformers/dependencies/geometryvalidator8/OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers/dependencies/geometryvalidator8/PLANAR_SURFACE.fme SELF_INTERSECTING CHECK_HOLE_TOUCHING_POLYGON]No]CONNECT_Z_MODE_SI]FIRST_WINS]SELF_INTERSECTION_TOLERANCE]None]FME_CONTROLLER_QUERY_FILE]transformers/dependencies/geometryvalidator8/SELF_INTERSECTING.fme SHELL_VALIDATION FLIP_APPEARANCE_MODE]FLIP_APPEARANCES]FME_CONTROLLER_QUERY_FILE]transformers/dependencies/geometryvalidator8/SHELL_VALIDATION.fme SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]0.0]FME_CONTROLLER_QUERY_FILE]transformers/dependencies/geometryvalidator8/TYPE_REPAIR.fme MISMATCHED_DIMENSIONS FORCE_DIMENSION]2D]FME_CONTROLLER_QUERY_FILE]transformers/dependencies/geometryvalidator8/MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers/dependencies/geometryvalidator8/MISSING_MEASURES_AND_ELEVATIONS.fme SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> Tester_2
Note: Garder que les frênes
Tester_2
    BOOL_OP = OR
    TEST_CLAUSE = CASE_INSENSITIVE_TEST @Value(ARH_ESSENCE) BEGINS_WITH FR
    TEST_MODE = CASE_INSENSITIVE_TEST
    PASSED -> PointOnAreaOverlayer_2 [POINT]
    FAILED -> Tester_2_Failed
Tester_2_Failed: Logger
    LOG_FEATURE = LOG_ONLY
    MAXCOORDS = 20
    MAXFEATS = 20
    MESSAGE = Feature is:
    SEVERITY = INFO

Bookmark: Photo
TIFF (reader TIFF_2)
    -> RasterPropertyExtractor
    -> Reprojector_7
Note: Reprojection en EPSG3857
Reprojector_7
    DEST = EPSG:3857
    INTERPOLATION_TYPE_NAME = Nearest Neighbor
    RASTER_CELL_SIZE = Preserve Cells
    RASTER_TOLERANCE = 0.0
    SOURCE = EPSG:32188
    REPROJECTED -> RasterResampler
    REPROJECTED -> PointCloudOnRasterComponentSetter [Raster]
Note: Redimensionner la photo à 1672x1711
RasterResampler
    COLUMNS = 1672
    INTERPOLATION_TYPE_NAME = Nearest Neighbor
    ROWCOL_OR_CELLSIZE = RowsColumns
    ROWS = 1711
    RESAMPLED -> RasterPyramider
    <REJECTED> -> RasterResampler__Rejected_
Note: Création de 10 niveaux de zoom
RasterPyramider
    INTERPOLATION_TYPE_NAME = Nearest Neighbor
    NUMBER_OF_LEVELS = 10
    NUM_PYRAMID_LEVELS_ATTRIBUTE = _num_pyramid_levels
    PYRAMID_LEVEL_ATTRIBUTE = _pyramid_level
    RASTER_INDEX_ATTRIBUTE = _raster_index
    SMALLESTSIZE_OR_NUMLEVELS = Number of Levels
    USE_POWERS_OF_TWO = No
    PYRAMIDS -> raster (writer TIFF_1)
    <REJECTED> -> RasterPyramider__Rejected_
Note: Création d'un tiff (seule façon de conserver l'apparence de la photo)
raster (writer TIFF_1)
    attributes: _raster_index largeint, _pyramid_level largeint, _num_pyramid_levels largeint
RasterPyramider__Rejected_: Logger
    LOG_FEATURE = LOG_ONLY
    MAXCOORDS = 20
    MAXFEATS = 20
    MESSAGE = Feature is:
    SEVERITY = INFO
RasterResampler__Rejected_: Logger
    LOG_FEATURE = LOG_ONLY
    MAXCOORDS = 20
    MAXFEATS = 20
    MESSAGE = Feature is:
    SEVERITY = INFO
RasterPropertyExtractor
    <REJECTED> -> RasterPropertyExtractor__Rejected_
RasterPropertyExtractor__Rejected_: Logger
    LOG_FEATURE = LOG_ONLY
    MAXCOORDS = 20
    MAXFEATS = 20
    MESSAGE = Feature is:
    SEVERITY = INFO

Bookmark: Arbres publics
CSV (reader CSV2_4)
    attributes: INV_TYPE varchar(2), EMP_NO real64, ARROND uint32, ARROND_NOM varchar(24), Rue varchar(1), COTE varchar(1), No_civique varchar(1), Emplacement varchar(24), Coord_X time, Coord_Y real64, SIGLE varchar(7), Essence_latin varchar(46), Essence_fr varchar(49), ESSENCE_ANG varchar(45), DHP real32, Date_releve varchar(20), Date_plantation varchar(20), LOCALISATION varchar(1), CODE_PARC varchar(9), NOM_PARC varchar(43), Longitude x_coordinate, Latitude y_coordinate
    -> Reprojector_3
Note: Reprojection de EPSG4326 vers EPSG3857
Reprojector_3
    DEST = EPSG:3857
    INTERPOLATION_TYPE_NAME = Nearest Neighbor
    RASTER_CELL_SIZE = Preserve Cells
    RASTER_TOLERANCE = 0.0
    SOURCE = EPSG:4326
    REPROJECTED -> GeometryExtractor_3
Note: Conversion des données en couches vectorielles
GeometryExtractor_3
    ATTR = _geometry
    KIND_LONG = FME Binary
    REMOVE_GEOMETRY = No
    -> GeometryValidator_3
Note: Valider si les données sont praticables
GeometryValidator_3
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme CONSECUTIVE_IDENTICAL_VERTICES_2D CHECK_Z]YES]FME_CONTROLLER_QUERY_FILE]transformers/dependencies/geometryvalidator8/CONSECUTIVE_IDENTICAL_VERTICES_2D.fme MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme NULL_REMOVAL FME_CONTROLLER_QUERY_FILE]transformers/dependencies/geometryvalidator8/NULL_REMOVAL.fme]FME_CONTROLLER_CHOICE]NULL_REMOVAL OGC_SIMPLE_CHECK LEGACY_OGC]No]FME_CONTROLLER_QUERY_FILE]transformers/dependencies/geometryvalidator8/OGC_SIMPLE_CHECK.fme OGC_VALID_CHECK OGC_VERSION]V1.2.0]FME_CONTROLLER_QUERY_FILE]transformers/dependencies/geometryvalidator8/OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers/dependencies/geometryvalidator8/PLANAR_SURFACE.fme SELF_INTERSECTING CHECK_HOLE_TOUCHING_POLYGON]No]CONNECT_Z_MODE_SI]FIRST_WINS]SELF_INTERSECTION_TOLERANCE]None]FME_CONTROLLER_QUERY_FILE]transformers/dependencies/geometryvalidator8/SELF_INTERSECTING.fme SHELL_VALIDATION FLIP_APPEARANCE_MODE]FLIP_APPEARANCES]FME_CONTROLLER_QUERY_FILE]transformers/dependencies/geometryvalidator8/SHELL_VALIDATION.fme SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]0.0]FME_CONTROLLER_QUERY_FILE]transformers/dependencies/geometryvalidator8/TYPE_REPAIR.fme MISMATCHED_DIMENSIONS FORCE_DIMENSION]2D]FME_CONTROLLER_QUERY_FILE]transformers/dependencies/geometryvalidator8/MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers/dependencies/geometryvalidator8/MISSING_MEASURES_AND_ELEVATIONS.fme SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> arbres_publics (writer POSTGIS_3)
    PASSED -> Tester
    <REJECTED> -> Logger_4
Note: Création de la couche de sortie vers PostGIS
arbres_publics (writer POSTGIS_3)
    attributes: no_civiq int8, rue varchar(52), rue_de varchar(54), rue_a varchar(45), nom_parc varchar(29), sigle varchar(7), nom_arrond varchar(42), invent varchar(13), coord_x time, coord_y float8, injections int8, longitude float8, latitude float8
Note: Filtrer tous les arbres dont l'attribut ''Essence_fr'' contiennent le nom ''Frêne''
Tester
    BOOL_OP = OR
    TEST_CLAUSE = CASE_INSENSITIVE_TEST @Value(Essence_fr) CONTAINS Frêne
    TEST_MODE = TEST
    PASSED -> Clipper_2 [CLIPPEE]
Logger_4
    LOG_FEATURE = LOG_ONLY
    MAXCOORDS = 20
    MAXFEATS = 20
    MESSAGE = Feature is:
    SEVERITY = INFO

Bookmark: Données lidar
LAS (reader LAS_1)
    -> PointCloudThinner
Note: Réduire le volume de points
PointCloudThinner
    INTERVAL = 30
    THINNED -> EsriReprojector
Note: Reprojection de EPSG:2950 vers EPSG:3857
Note: Associer les couleurs du raster aux points
EsriReprojector
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_DIRECTION = Forward
    GEOTRANSFORMATION_NAME = NAD_1983_CSRS_To_WGS_1984
    INTERPOLATION_TYPE_NAME = Nearest Neighbor
    RASTER_CELL_SIZE = Preserve Cells
    RASTER_TOLERANCE = 0.0
    SOURCE = ESRIWKT|NAD_1983_CSRS_MTM_8|PROJCS["NAD_1983_CSRS_MTM_8",GEOGCS["GCS_North_American_1983_CSRS",DATUM["D_North_American_1983_CSRS",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    REPROJECTED -> PointCloudOnRasterComponentSetter [PointCloud]

Bookmark: Associer les couleurs du raster aux points
Note: Joindre les infos. du raster aux points
PointCloudOnRasterComponentSetter
    COMPONENT_SPECIFICATION = Color
    DEFAULT_VALUES_OVERWRITE_DATA = No
    EXTRACT_NODATA = No
    INTERPOLATION = Nearest Neighbor
    PointCloud -> PointCloudFilter
    <REJECTED> -> Logger_3
PointCloudFilter
    FILTER_TABLE = @Component(color_red)!=0&&@Component(color_blue)!=0&&@Component(color_green) @Component(color_red)!=0 && @Component(color_green)!=0  && @Component(color_blue)!=0
    OUTPUT_UNFILTERED_POINTS = Yes
    @Component(color_red)!=0 && @Component(color_green)!=0 && @Component(color_blue)!=0 -> PointCloudCoercer
    <UNFILTERED> -> PointCloudCoercer
    <REJECTED> -> Logger_2
Note: Transformer le nuage de ponts en couche vectorielle
PointCloudCoercer
    ACCUM_ATTRS_NAME = Yes
    CONVERT_TO_DISPLAY = Individual Points
    PART_NUMBER_ATTR_NAME = _part_number
    POINT_COMPONENTS = color_red color_green color_blue z
    POINT_COMPONENTS_PRESERVE_DISPLAY = Attributes
    COERCED -> BoundingBoxAccumulator
    COERCED -> PointOnAreaOverlayer [POINT]
    <REJECTED> -> Logger
Logger
    LOG_FEATURE = LOG_ONLY
    MAXCOORDS = 20
    MAXFEATS = 20
    MESSAGE = Feature is:
    SEVERITY = INFO
Logger_2
    LOG_FEATURE = LOG_ONLY
    MAXCOORDS = 20
    MAXFEATS = 20
    MESSAGE = Feature is:
    SEVERITY = INFO
Logger_3
    LOG_FEATURE = LOG_ONLY
    MAXCOORDS = 20
    MAXFEATS = 20
    MESSAGE = Feature is:
    SEVERITY = INFO

Bookmark: Préparer la jointure entre les frênes publics et les données lidars
Note: Tracer un polygone qui représente la superficie du nuage de points
BoundingBoxAccumulator
    ACCUM_ATTRS_NAME = Use Attributes From One Feature
    BOUNDING_BOX -> Clipper_2 [CLIPPER]
Note: Conserver les arbres à l'intérieur de la tuile lidar
Clipper_2
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Bufferer
    <REJECTED> -> Logger_5
Note: Tracer une zone tampon autour du centre des arbres
Bufferer
    ANGLE = 22.5
    CAP_STYLE = Round
    CORNER_STYLE = Arc
    MODE = AREA
    OFFSET = 0.2
    OFFSET_UNITS = METERS
    PRECISION = APPROX
    BUFFERED -> PointOnAreaOverlayer [AREA]
    <REJECTED> -> Logger_6
Logger_6
    LOG_FEATURE = LOG_ONLY
    MAXCOORDS = 20
    MAXFEATS = 20
    MESSAGE = Feature is:
    SEVERITY = INFO
Logger_5
    LOG_FEATURE = LOG_ONLY
    MAXCOORDS = 20
    MAXFEATS = 20
    MESSAGE = Feature is:
    SEVERITY = INFO

Bookmark: Jointure spatiale
Note: Superposer les points lidar sur les zones tampons des frênes
PointOnAreaOverlayer
    ATTR_ACCUM_MODE = Merge Incoming
    ATTR_CONFLICT_RES = Use Incoming
    DEAGGREGATE_INPUT = Yes
    OV_ATTR = _overlaps
    POLYS_FIRST = NO
    AREA -> AttributeManager
    <REJECTED> -> Logger_7
Logger_7
    LOG_FEATURE = LOG_ONLY
    MAXCOORDS = 20
    MAXFEATS = 20
    MESSAGE = Feature is:
    SEVERITY = INFO
    LOGGED -> AttributeManager
Note: Éliminer les champs inutiles
AttributeManager
    ATTR_TABLE:
      REMOVE INV_TYPE
      REMOVE EMP_NO
      REMOVE ARROND
      REMOVE Rue
      REMOVE COTE
      REMOVE No_civique
      REMOVE SIGLE
      REMOVE Essence_latin
      REMOVE ESSENCE_ANG
      REMOVE DHP
      REMOVE LOCALISATION
      REMOVE CODE_PARC
      REMOVE _geometry
      REMOVE _clipped
      REMOVE _overlaps
    USER_EXPOSED_ATTRIBUTES = Coord_Z
    -> AttributeFilter_2
Note: Éliminer les entrées aux valeurs ''missing''
AttributeFilter_2
    ATTR_NAME = z
    ATTR_VALUES = <Empty>,<Missing>,<Null>,<Unfiltered>
    <UNFILTERED> -> frene_lidar (writer POSTGIS_9)
Note: Très peu de résultats sortants, laisse croire que les données des arbres lidar ne correspondent pas celles des arbres publics.
frene_lidar (writer POSTGIS_9)
    attributes: coord_z varchar(200), arrond_nom varchar(24), emplacement varchar(24), coord_x time, coord_y float8, essence_fr varchar(49), date_releve varchar(20), date_plantation varchar(20), nom_parc varchar(43), longitude float8, latitude float8, z text, _part_number numeric(20,0), fme_rejection_code text, color_red text, color_green text, color_blue text

Bookmark: Limites des arrondissements
limites-administratives-agglomeration-nad83 (reader GEOJSON_1)
    attributes: CODEID int, NOM string, NOM_OFFICIEL string, CODEMAMH string, CODE_3C string, NUM int, ABREV string, TYPE string, COMMENT string, DATEMODIF string
    -> EsriReprojector_2
Note: Reprojection de EPSG:32188 vers EPSG:4326
EsriReprojector_2
    DEST = ESRIWKT|GCS_WGS_1984|GEOGCS["GCS_WGS_1984",DATUM["D_WGS_1984",SPHEROID["WGS_1984",6378137.0,298.257223563]],PRIMEM["Greenwich",0.0],UNIT["Degree",0.0174532925199433]]
    GEOTRANSFORMATION_DIRECTION = Forward
    GEOTRANSFORMATION_NAME = NAD_1983_CSRS_To_WGS_1984
    INTERPOLATION_TYPE_NAME = Nearest Neighbor
    RASTER_CELL_SIZE = Preserve Cells
    RASTER_TOLERANCE = 0.0
    SOURCE = ESRIWKT|NAD_1983_MTM_8|PROJCS["NAD_1983_MTM_8",GEOGCS["GCS_North_American_1983",DATUM["D_North_American_1983",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    REPROJECTED -> H3HexagonalIndexer_2

Bookmark: Création des tuiles hexagonales
Note: Création d'hexagones de 200m par côté
H3HexagonalIndexer_2
    INDEX_OPERATION = Filling Indexes
    -> Reprojector_9
    <REJECTED> -> H3HexagonalIndexer_2__Rejected_
Note: Reprojection de EPSG:2950 vers EPSG:3857
Reprojector_9
    DEST = EPSG:3857
    INTERPOLATION_TYPE_NAME = Nearest Neighbor
    RASTER_CELL_SIZE = Preserve Cells
    RASTER_TOLERANCE = 0.0
    SOURCE = 4326
    REPROJECTED -> PointOnAreaOverlayer_2 [AREA]
    REPROJECTED -> PointOnAreaOverlayer_3 [AREA]
H3HexagonalIndexer_2__Rejected_: Logger
    LOG_FEATURE = LOG_ONLY
    MAXCOORDS = 20
    MAXFEATS = 20
    MESSAGE = Feature is:
    SEVERITY = INFO

Bookmark: Densité des arbres abattus
Note: Jointure spatiale
PointOnAreaOverlayer_2
    ATTR_ACCUM_MODE = Merge Incoming
    ATTR_CONFLICT_RES = Use Incoming
    DEAGGREGATE_INPUT = Yes
    OV_ATTR = _overlaps
    POLYS_FIRST = NO
    AREA -> AttributeKeeper_2
    <REJECTED> -> PointOnAreaOverlayer_2__Rejected_
Note: On garde seulement les champs voulus
AttributeKeeper_2
    CREATE_BULK_MODE_FEATURES = NO
    KEEP_ATTRS = point_count,_geometry,_h3index
    -> AttributeManager_3
Note: Ménage des champs inutiles
AttributeManager_3
    ATTR_TABLE = REMOVE _geometry
    -> densite_frene_abattus (writer POSTGIS_9)
Note: Envoi vers PostGIS
densite_frene_abattus (writer POSTGIS_9)
    attributes: _h3index numeric(20,0)
PointOnAreaOverlayer_2__Rejected_: Logger
    LOG_FEATURE = LOG_ONLY
    MAXCOORDS = 20
    MAXFEATS = 20
    MESSAGE = Feature is:
    SEVERITY = INFO

Bookmark: Frênes protégés
Note: Données des frênes injectés à l'insecticide sous forme de table
CSV (reader CSV2_2)
    attributes: no_civiq uint32, Rue varchar(52), Rue_De varchar(54), Rue_A varchar(45), Nom_parc varchar(29), Sigle varchar(7), Nom_arrond varchar(42), Invent varchar(13), Coord_X time, Coord_Y real64, Injections uint32, Longitude x_coordinate, Latitude y_coordinate
    -> Reprojector_2
Note: Reprojection de EPSG:2950 vers EPSG:3857
Reprojector_2
    DEST = EPSG:3857
    INTERPOLATION_TYPE_NAME = Nearest Neighbor
    RASTER_CELL_SIZE = Preserve Cells
    RASTER_TOLERANCE = 0.0
    SOURCE = EPSG:4326
    REPROJECTED -> GeometryExtractor_2
Note: Conversion des données en couches vectorielles
GeometryExtractor_2
    ATTR = _geometry
    KIND_LONG = FME Binary
    REMOVE_GEOMETRY = No
    -> GeometryValidator_2
Note: Valider si les données sont praticables
GeometryValidator_2
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme CONSECUTIVE_IDENTICAL_VERTICES_2D CHECK_Z]YES]FME_CONTROLLER_QUERY_FILE]transformers/dependencies/geometryvalidator8/CONSECUTIVE_IDENTICAL_VERTICES_2D.fme MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme NULL_REMOVAL FME_CONTROLLER_QUERY_FILE]transformers/dependencies/geometryvalidator8/NULL_REMOVAL.fme]FME_CONTROLLER_CHOICE]NULL_REMOVAL OGC_SIMPLE_CHECK LEGACY_OGC]No]FME_CONTROLLER_QUERY_FILE]transformers/dependencies/geometryvalidator8/OGC_SIMPLE_CHECK.fme OGC_VALID_CHECK OGC_VERSION]V1.2.0]FME_CONTROLLER_QUERY_FILE]transformers/dependencies/geometryvalidator8/OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers/dependencies/geometryvalidator8/PLANAR_SURFACE.fme SELF_INTERSECTING CHECK_HOLE_TOUCHING_POLYGON]No]CONNECT_Z_MODE_SI]FIRST_WINS]SELF_INTERSECTION_TOLERANCE]None]FME_CONTROLLER_QUERY_FILE]transformers/dependencies/geometryvalidator8/SELF_INTERSECTING.fme SHELL_VALIDATION FLIP_APPEARANCE_MODE]FLIP_APPEARANCES]FME_CONTROLLER_QUERY_FILE]transformers/dependencies/geometryvalidator8/SHELL_VALIDATION.fme SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]0.0]FME_CONTROLLER_QUERY_FILE]transformers/dependencies/geometryvalidator8/TYPE_REPAIR.fme MISMATCHED_DIMENSIONS FORCE_DIMENSION]2D]FME_CONTROLLER_QUERY_FILE]transformers/dependencies/geometryvalidator8/MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers/dependencies/geometryvalidator8/MISSING_MEASURES_AND_ELEVATIONS.fme SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> PointOnAreaOverlayer_3 [POINT]

Bookmark: Densité des frênes protégés
PointOnAreaOverlayer_3
    ATTR_ACCUM_MODE = Merge Incoming
    ATTR_CONFLICT_RES = Use Original
    DEAGGREGATE_INPUT = Yes
    OV_ATTR = _overlaps
    POLYS_FIRST = YES
    AREA -> AttributeKeeper_3
    <REJECTED> -> PointOnAreaOverlayer_3__Rejected_
Note: On garde seulement les champs voulus
AttributeKeeper_3
    CREATE_BULK_MODE_FEATURES = NO
    KEEP_ATTRS = point_count,_geometry,_h3index
    -> AttributeManager_2
Note: Ménage des champs inutiles
AttributeManager_2
    ATTR_TABLE = REMOVE _geometry
    -> densite_frenes_proteges (writer POSTGIS_9)
Note: Envoi vers PostGIS
densite_frenes_proteges (writer POSTGIS_9)
    attributes: _h3index numeric(20,0)
PointOnAreaOverlayer_3__Rejected_: Logger
    LOG_FEATURE = LOG_ONLY
    MAXCOORDS = 20
    MAXFEATS = 20
    MESSAGE = Feature is:
    SEVERITY = INFO

Bookmark: Toutes les données de canopée de 2007 par arrondissements
canopee-2007-ahuntsic-cartierville (reader SHAPEFILE_1)
    -> Reprojector_4
canopee-2007-anjou (reader SHAPEFILE_2)
    -> Reprojector_4
canopee-2007-cdn-ndg (reader SHAPEFILE_3)
    -> Reprojector_4
canopee-2007-ile-bizard-sainte-genevieve (reader SHAPEFILE_4)
    -> Reprojector_4
canopee-2007-lachine (reader SHAPEFILE_5)
    -> Reprojector_4
canopee-2007-lasalle (reader SHAPEFILE_6)
    -> Reprojector_4
canopee-2007-le-plateau-mont-royal (reader SHAPEFILE_7)
    -> Reprojector_4
canopee-2007-le-sud-ouest (reader SHAPEFILE_8)
    -> Reprojector_4
canopee-2007-mercier-hochelaga-maisonneuve (reader SHAPEFILE_9)
    -> Reprojector_4
canopee-2007-montreal-nord (reader SHAPEFILE_10)
    -> Reprojector_4
canopee-2007-outremont (reader SHAPEFILE_11)
    -> Reprojector_4
canopee-2007-pierrefonds-roxboro (reader SHAPEFILE_12)
    -> Reprojector_4
canopee-2007-rdp-pat (reader SHAPEFILE_13)
    -> Reprojector_4
canopee-2007-rosemont-la-petite-patrie (reader SHAPEFILE_14)
    -> Reprojector_4
canopee-2007-saint-laurent (reader SHAPEFILE_15)
    -> Reprojector_4
canopee-2007-saint-leonard (reader SHAPEFILE_16)
    -> Reprojector_4
canopee-2007-verdun (reader SHAPEFILE_17)
    -> Reprojector_4
canopee-2007-ville-marie (reader SHAPEFILE_18)
    -> Reprojector_4
canopee-2007-villeray-saint-michel-parc-extension (reader SHAPEFILE_20)
    -> Reprojector_4

Bookmark: canopée 2007
Note: (insérés individuellement, avant de savoir qu'il était possible d'en ajouter plusieurs à la fois: très long à refaire à partir de One Drive...)
Note: Reprojection en EPSG3857
Reprojector_4
    DEST = EPSG:3857
    INTERPOLATION_TYPE_NAME = Nearest Neighbor
    RASTER_CELL_SIZE = Preserve Cells
    RASTER_TOLERANCE = 0.0
    REPROJECTED -> GeometryExtractor_4
Note: Conversion des données en couches vectorielles
GeometryExtractor_4
    ATTR = _geometry
    KIND_LONG = FME Binary
    REMOVE_GEOMETRY = No
    -> cannopee_2007 (writer POSTGIS_5)
Note: Création de la couche de sortie vers PostGIS
cannopee_2007 (writer POSTGIS_5)
    attributes: _geometry text

Bookmark: Canopée 2015
Note: Données de la canopée en 2015
canopee-2015 (reader SHAPEFILE_21)
    -> Reprojector_6
Note: Reprojection en EPSG3857
Reprojector_6
    DEST = EPSG:3857
    INTERPOLATION_TYPE_NAME = Nearest Neighbor
    RASTER_CELL_SIZE = Preserve Cells
    RASTER_TOLERANCE = 0.0
    REPROJECTED -> GeometryExtractor_6
Note: Conversion des données en couches vectorielles
GeometryExtractor_6
    ATTR = _geometry
    KIND_LONG = FME Binary
    REMOVE_GEOMETRY = No
    -> cannopee_2015 (writer POSTGIS_4)
cannopee_2015 (writer POSTGIS_4)
    attributes: _geometry text

Bookmark: Canopée 2019
Note: Données de la canopée en 2019
canopee-2019 (reader SHAPEFILE_19)
    -> Reprojector_5
Note: Reprojection en EPSG3857
Reprojector_5
    DEST = EPSG:3857
    INTERPOLATION_TYPE_NAME = Nearest Neighbor
    RASTER_CELL_SIZE = Preserve Cells
    RASTER_TOLERANCE = 0.0
    REPROJECTED -> GeometryExtractor_5
Note: Conversion des données en couches vectorielles
GeometryExtractor_5
    ATTR = _geometry
    KIND_LONG = FME Binary
    REMOVE_GEOMETRY = No
    -> cannopee_2019 (writer POSTGIS_4)
cannopee_2019 (writer POSTGIS_4)
    attributes: _geometry text
